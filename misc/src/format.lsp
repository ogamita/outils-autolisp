;;; format.lsp --- Sous-ensemble de Common Lisp FORMAT pour misc

(setq format 'format)

(defun format--fail (message)
  (prompt (strcat "\nformat: " message))
  (error message))

(defun format--digit-p (ch)
  (and (>= (ascii ch) 48) (<= (ascii ch) 57)))

(defun format--uppercase (s)
  (strcase s))

(defun format--repeat (text count / acc)
  (setq acc "")
  (while (> count 0)
    (setq acc (strcat acc text))
    (setq count (1- count)))
  acc)

(defun format--list-length (items / count)
  (setq count 0)
  (while items
    (setq count (1+ count))
    (setq items (cdr items)))
  count)

(defun format--listish-p (value / kind)
  (or (null value)
      (= (setq kind (type value)) 'LIST)))

(defun format--pad-right (s width padchar / result)
  (setq result s)
  (while (< (strlen result) width)
    (setq result (strcat result padchar)))
  result)

(defun format--pad-left (s width padchar / result)
  (setq result s)
  (while (< (strlen result) width)
    (setq result (strcat padchar result)))
  result)

(defun format--line-col (text / idx ch col)
  (setq idx 1 col 0)
  (while (<= idx (strlen text))
    (setq ch (substr text idx 1))
    (if (= ch "\n")
      (setq col 0)
      (setq col (1+ col)))
    (setq idx (1+ idx)))
  col)

(defun format--append-piece (acc piece /)
  (list
    (strcat (nth 0 acc) piece)
    (nth 1 acc)
    (format--line-col (strcat (format--repeat " " (nth 2 acc)) piece))))

(defun format--nth-or-nil (idx items /)
  (if (and items (>= idx 0))
    (nth idx items)
    nil))

(defun format--consume-arg (args /)
  (if args
    (list (car args) (cdr args))
    (format--fail "argument manquant")))

(defun format--integer (value / kind)
  (setq kind (type value))
  (cond
    ((or (= kind 'INT) (= kind 'REAL)) (fix value))
    (T (format--fail "entier attendu"))))

(defun format--number (value / kind)
  (setq kind (type value))
  (cond
    ((or (= kind 'INT) (= kind 'REAL)) value)
    (T (format--fail "nombre attendu"))))

(defun format--char-string (value /)
  (if (and (= (type value) 'STR) (> (strlen value) 0))
    (substr value 1 1)
    (format--fail "chaîne non vide attendue pour ~C")))

(defun format--radix (n base / digits negative value rem result)
  (setq digits "0123456789ABCDEF")
  (setq negative (< n 0))
  (setq value (abs n))
  (setq result "")
  (if (= value 0)
    (setq result "0")
    (while (> value 0)
      (setq rem (rem value base))
      (setq result (strcat (substr digits (1+ rem) 1) result))
      (setq value (/ (- value rem) base))))
  (if negative
    (strcat "-" result)
    result))

(defun format--resolve-parameter (param args / taken)
  (cond
    ((null param) (list nil args))
    ((= param ':V)
      (setq taken (format--consume-arg args))
      (list (format--integer (car taken)) (cadr taken)))
    ((and (= (type param) 'LIST) (= (car param) ':CHAR))
      (list (cadr param) args))
    (T (list param args))))

(defun format--resolve-padchar (param args default / taken value)
  (if (null param)
    (list default args)
    (progn
      (setq taken (format--resolve-parameter param args))
      (setq value (car taken) args (cadr taken))
      (list (format--char-string value) args))))

(defun format--flag-present-p (flag flags)
  (not (null (member flag flags))))

(defun format--ensure-flags (flags allow-colon allow-at /)
  (if (and (format--flag-present-p ":" flags) (not allow-colon))
    (format--fail "modificateur : non supporté pour cette directive"))
  (if (and (format--flag-present-p "@" flags) (not allow-at))
    (format--fail "modificateur @ non supporté pour cette directive"))
  T)

(defun format--ensure-param-count (params max-count / tail)
  (setq tail params)
  (while (and tail (> max-count 0))
    (setq tail (cdr tail))
    (setq max-count (1- max-count)))
  (if tail
    (format--fail "trop de paramètres pour cette directive"))
  T)

(defun format--parse-directive (control start / idx len params token ch flags spec)
  (setq idx start len (strlen control) params nil token "")
  (while (<= idx len)
    (setq ch (substr control idx 1))
    (cond
      ((or (= ch "@") (= ch ":"))
        (setq flags (cons ch flags))
        (setq idx (1+ idx)))
      ((= ch ",")
        (if (/= token "")
          (progn
            (setq params (append params (list (atoi token))))
            (setq token ""))
          (setq params (append params (list nil))))
        (setq idx (1+ idx)))
      ((format--digit-p ch)
        (setq token (strcat token ch))
        (setq idx (1+ idx)))
      ((or (= ch "V") (= ch "v"))
        (if (/= token "")
          (format--fail "paramètre invalide"))
        (setq params (append params (list ':V)))
        (setq idx (1+ idx)))
      ((= ch "'")
        (if (< idx len)
          (progn
            (setq params (append params (list (list ':CHAR (substr control (1+ idx) 1)))))
            (setq idx (+ idx 2)))
          (format--fail "caractère manquant après quote")))
      (T
        (if (/= token "")
          (setq params (append params (list (atoi token)))))
        (setq spec ch)
        (setq idx (1+ idx))
        (setq ch nil)
        (setq len 0))))
  (if (null spec)
    (format--fail "directive incomplète")
    (list params flags spec idx)))

(defun format--find-matching-brace (control start / idx len depth parsed spec)
  (setq idx start len (strlen control) depth 1)
  (while (and (<= idx len) (> depth 0))
    (if (= (substr control idx 1) "~")
      (progn
        (setq parsed (format--parse-directive control (1+ idx)))
        (setq spec (format--uppercase (nth 2 parsed)))
        (cond
          ((= spec "{") (setq depth (1+ depth)))
          ((= spec "}") (setq depth (1- depth))))
        (setq idx (nth 3 parsed)))
      (setq idx (1+ idx))))
  (if (/= depth 0)
    (format--fail "directive ~{ sans ~} correspondant")
    idx))

(defun format--apply-width-left (text width)
  (if (and width (> width 0))
    (format--pad-right text width " ")
    text))

(defun format--apply-width-right (text width)
  (if (and width (> width 0))
    (format--pad-left text width " ")
    text))

(defun format--apply-width-left-with-pad (text width padchar)
  (if (and width (> width 0))
    (format--pad-right text width padchar)
    text))

(defun format--apply-width-right-with-pad (text width padchar)
  (if (and width (> width 0))
    (format--pad-left text width padchar)
    text))

(defun format--float-string (value decimals colonp / precision)
  (setq precision (if decimals decimals 2))
  (if colonp
    (setq value (angtos (float value) 0 precision))
    (setq value (rtos (float value) 2 precision)))
  (if (and precision (>= precision 0))
    (format--with-decimals value precision)
    value))

(defun format--with-decimals (text decimals / dot needed)
  (setq dot (vl-string-search "." text))
  (if (< decimals 1)
    (if dot
      (substr text 1 dot)
      text)
    (if dot
      (progn
        (setq needed (- decimals (- (strlen text) dot 1)))
        (if (> needed 0)
          (strcat text (format--repeat "0" needed))
          text))
      (strcat text "." (format--repeat "0" decimals)))))

(defun format--render-simple (spec params flags args / upper width take obj text precision n colonp atp p1 p2 p3 p4 padchar)
  (setq upper (format--uppercase spec))
  (setq colonp (format--flag-present-p ":" flags))
  (setq atp (format--flag-present-p "@" flags))
  (cond
    ((= upper "A")
      (format--ensure-flags flags nil nil)
      (format--ensure-param-count params 4)
      (setq p1 (format--resolve-parameter (car params) args))
      (setq width (car p1) args (cadr p1))
      (setq p4 (format--resolve-padchar (format--nth-or-nil 3 params) args " "))
      (setq padchar (car p4) args (cadr p4))
      (setq take (format--consume-arg args) obj (car take) args (cadr take))
      (setq text (vl-princ-to-string obj))
      (list (format--apply-width-left-with-pad text width padchar) args))
    ((= upper "S")
      (format--ensure-flags flags nil nil)
      (format--ensure-param-count params 4)
      (setq p1 (format--resolve-parameter (car params) args))
      (setq width (car p1) args (cadr p1))
      (setq p4 (format--resolve-padchar (format--nth-or-nil 3 params) args " "))
      (setq padchar (car p4) args (cadr p4))
      (setq take (format--consume-arg args) obj (car take) args (cadr take))
      (setq text (vl-prin1-to-string obj))
      (list (format--apply-width-left-with-pad text width padchar) args))
    ((= upper "D")
      (format--ensure-flags flags nil nil)
      (format--ensure-param-count params 2)
      (setq p1 (format--resolve-parameter (car params) args))
      (setq width (car p1) args (cadr p1))
      (setq p2 (format--resolve-padchar (format--nth-or-nil 1 params) args " "))
      (setq padchar (car p2) args (cadr p2))
      (setq take (format--consume-arg args) obj (car take) args (cadr take))
      (setq text (itoa (format--integer obj)))
      (list (format--apply-width-right-with-pad text width padchar) args))
    ((= upper "B")
      (format--ensure-flags flags nil nil)
      (format--ensure-param-count params 2)
      (setq p1 (format--resolve-parameter (car params) args))
      (setq width (car p1) args (cadr p1))
      (setq p2 (format--resolve-padchar (format--nth-or-nil 1 params) args " "))
      (setq padchar (car p2) args (cadr p2))
      (setq take (format--consume-arg args) obj (car take) args (cadr take))
      (setq text (format--radix (format--integer obj) 2))
      (list (format--apply-width-right-with-pad text width padchar) args))
    ((= upper "O")
      (format--ensure-flags flags nil nil)
      (format--ensure-param-count params 2)
      (setq p1 (format--resolve-parameter (car params) args))
      (setq width (car p1) args (cadr p1))
      (setq p2 (format--resolve-padchar (format--nth-or-nil 1 params) args " "))
      (setq padchar (car p2) args (cadr p2))
      (setq take (format--consume-arg args) obj (car take) args (cadr take))
      (setq text (format--radix (format--integer obj) 8))
      (list (format--apply-width-right-with-pad text width padchar) args))
    ((= upper "X")
      (format--ensure-flags flags nil nil)
      (format--ensure-param-count params 2)
      (setq p1 (format--resolve-parameter (car params) args))
      (setq width (car p1) args (cadr p1))
      (setq p2 (format--resolve-padchar (format--nth-or-nil 1 params) args " "))
      (setq padchar (car p2) args (cadr p2))
      (setq take (format--consume-arg args) obj (car take) args (cadr take))
      (setq text (format--radix (format--integer obj) 16))
      (list (format--apply-width-right-with-pad text width padchar) args))
    ((= upper "F")
      (format--ensure-flags flags T nil)
      (format--ensure-param-count params 2)
      (setq p1 (format--resolve-parameter (car params) args))
      (setq width (car p1) args (cadr p1))
      (setq p2 (format--resolve-parameter (cadr params) args))
      (setq precision (car p2) args (cadr p2))
      (setq take (format--consume-arg args) obj (car take) args (cadr take))
      (setq text (format--float-string (format--number obj) precision colonp))
      (list (format--apply-width-right text width) args))
    ((= upper "C")
      (format--ensure-flags flags nil T)
      (format--ensure-param-count params 0)
      (setq take (format--consume-arg args) obj (car take) args (cadr take))
      (setq text (format--char-string obj))
      (if atp (setq text (strcat "#\\" text)))
      (list text args))
    ((= upper "%")
      (format--ensure-flags flags nil nil)
      (format--ensure-param-count params 1)
      (setq p1 (format--resolve-parameter (car params) args))
      (setq n (if (car p1) (car p1) 1) args (cadr p1))
      (list (format--repeat "\n" n) args))
    ((= upper "&")
      (format--ensure-flags flags nil nil)
      (format--ensure-param-count params 1)
      (setq p1 (format--resolve-parameter (car params) args))
      (setq n (if (car p1) (car p1) 1) args (cadr p1))
      (list (list ':FRESH-LINE n) args))
    ((= upper "~")
      (format--ensure-flags flags nil nil)
      (format--ensure-param-count params 1)
      (setq p1 (format--resolve-parameter (car params) args))
      (setq n (if (car p1) (car p1) 1) args (cadr p1))
      (list (format--repeat "~" n) args))
    (T
      (format--fail (strcat "directive non supportée: ~" spec)))))

(defun format--render-iteration (body params flags args col / upper count p1 limit colonp atp taken seq subargs idx iteration rendered piece newargs after oldlen)
  (format--ensure-param-count params 1)
  (setq p1 (format--resolve-parameter (car params) args))
  (setq limit (car p1) args (cadr p1))
  (setq colonp (format--flag-present-p ":" flags))
  (setq atp (format--flag-present-p "@" flags))
  (setq idx 0 piece "")
  (cond
    ((and colonp atp)
      (while (and args (or (null limit) (< idx limit)))
        (setq taken (format--consume-arg args))
        (setq subargs (car taken))
        (if (not (format--listish-p subargs))
          (format--fail "liste d'arguments attendue pour ~:@{"))
        (setq after (cadr taken))
        (setq rendered (format--render-segment body 1 subargs col))
        (setq piece (strcat piece (nth 0 rendered)))
        (setq args after)
        (setq col (nth 2 rendered))
        (setq idx (1+ idx))))
    (colonp
      (setq taken (format--consume-arg args))
      (setq seq (car taken) args (cadr taken))
      (if (not (format--listish-p seq))
        (format--fail "liste de listes attendue pour ~:{"))
      (while (and seq (or (null limit) (< idx limit)))
        (setq subargs (car seq))
        (if (not (format--listish-p subargs))
          (format--fail "sous-liste d'arguments attendue pour ~:{"))
        (setq rendered (format--render-segment body 1 subargs col))
        (setq piece (strcat piece (nth 0 rendered)))
        (setq col (nth 2 rendered))
        (setq seq (cdr seq))
        (setq idx (1+ idx))))
    (atp
      (while (and args (or (null limit) (< idx limit)))
        (setq oldlen (format--list-length args))
        (setq rendered (format--render-segment body 1 args col))
        (setq newargs (nth 1 rendered))
        (if (= oldlen (format--list-length newargs))
          (format--fail "la sous-chaîne de ~@{ ne consomme aucun argument"))
        (setq piece (strcat piece (nth 0 rendered)))
        (setq args newargs)
        (setq col (nth 2 rendered))
        (setq idx (1+ idx))))
    (T
      (setq taken (format--consume-arg args))
      (setq seq (car taken) args (cadr taken))
      (if (not (format--listish-p seq))
        (format--fail "liste d'arguments attendue pour ~{"))
      (while (and seq (or (null limit) (< idx limit)))
        (setq oldlen (format--list-length seq))
        (setq rendered (format--render-segment body 1 seq col))
        (setq newargs (nth 1 rendered))
        (if (= oldlen (format--list-length newargs))
          (format--fail "la sous-chaîne de ~{ ne consomme aucun argument"))
        (setq piece (strcat piece (nth 0 rendered)))
        (setq seq newargs)
        (setq col (nth 2 rendered))
        (setq idx (1+ idx)))))
  (list piece args col))

(defun format--render-segment (control start args col / idx len out parsed params flags spec upper next text piece rendered brace-end body fresh)
  (setq idx start len (strlen control) out "")
  (while (<= idx len)
    (if (= (substr control idx 1) "~")
      (progn
        (setq parsed (format--parse-directive control (1+ idx)))
        (setq params (nth 0 parsed)
              flags (nth 1 parsed)
              spec  (nth 2 parsed)
              next  (nth 3 parsed)
              upper (format--uppercase spec))
        (cond
          ((= upper "}")
            (setq idx (1+ len)))
          ((= upper "{")
            (setq brace-end (format--find-matching-brace control next))
            (setq body (substr control next (- brace-end next 2)))
            (setq rendered (format--render-iteration body params flags args col))
            (setq out (strcat out (nth 0 rendered)))
            (setq args (nth 1 rendered))
            (setq col (nth 2 rendered))
            (setq idx brace-end))
          (T
            (setq rendered (format--render-simple spec params flags args))
            (setq piece (car rendered) args (cadr rendered))
            (if (and (= (type piece) 'LIST) (= (car piece) ':FRESH-LINE))
              (progn
                (setq fresh (cadr piece))
                (if (= col 0)
                  (setq piece (format--repeat "\n" (if (> fresh 0) (1- fresh) 0)))
                  (setq piece (format--repeat "\n" fresh))))
              nil)
            (setq out (strcat out piece))
            (setq col (format--line-col out))
            (setq idx next))))
      (progn
        (setq text (substr control idx 1))
        (setq out (strcat out text))
        (setq col (format--line-col out))
        (setq idx (1+ idx)))))
  (list out args col))

(defun format--format (control args / rendered)
  (if (/= (type control) 'STR)
    (format--fail "chaîne de contrôle attendue"))
  (if (not (format--listish-p args))
    (format--fail "liste d'arguments attendue"))
  (setq rendered (format--render-segment control 1 args 0))
  (nth 0 rendered))

(defun format (control args / result)
  (setq result (vl-catch-all-apply 'format--format (list control args)))
  (if (vl-catch-all-error-p result)
    (progn
      (prompt
        (strcat
          "\nformat: "
          (vl-catch-all-error-message result)))
      nil)
    result))
