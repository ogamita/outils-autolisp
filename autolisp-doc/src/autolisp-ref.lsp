;;; autolisp-ref.lsp --- Generated AutoLISP reference extracted from Autodesk Help
;;;
;;; Source: https://help.autodesk.com/view/OARX/2023/ENU/?guid=GUID-4CEE5072-8817-4920-8A2D-7060F5E16547
;;; Generated by autolisp-doc/scripts/build_autolisp_ref.py

(setq *autolisp-reference-parts* nil)

(setq *autolisp-reference-parts*
  (cons
    '(("*" .
          ((name . "*")
           (title . "* (multiply) (AutoLISP)")
           (summary . "Returns the product of all numbers")
           (source-kind . "AutoLISP")
           (alphabetic-group . "Non-alphabetic")
           (feature-groups . ("Arithmetic"))
           (supported-platforms . "Windows and Mac OS")
           (signature . "(* [number number ...])")
           (arguments . (("number" . "Type: Integer or Real\nA numeric value.")))
           (return-values . "Type: Integer or Real\nThe result of the multiplication. If you supply only one number argument, this function returns the result of multiplying it by one; it returns the number. Supplying no arguments returns 0.")
           (release-information . nil)
           (history . nil)
           (examples . "(* 2 3)\n6\n\n(* 2 3.0)\n6.0\n\n(* 2 3 4.0)\n24.0\n\n(* 3 -4.5)\n-13.5\n\n(* 3)\n3")
           (url . "https://help.autodesk.com/cloudhelp/2023/ENU/AutoCAD-AutoLISP-Reference/files/GUID-F7AABF2A-D2D2-4B8A-913C-98082ECB5B8D.htm")
           (guid . "GUID-F7AABF2A-D2D2-4B8A-913C-98082ECB5B8D"))))
    *autolisp-reference-parts*))

(setq *autolisp-reference-parts*
  (cons
    '(("*error*" .
          ((name . "*error*")
           (title . "*error* (AutoLISP)")
           (summary . "A user-definable error-handling function")
           (source-kind . "AutoLISP")
           (alphabetic-group . "Non-alphabetic")
           (feature-groups . ("Error-Handling"))
           (supported-platforms . "Windows and Mac OS")
           (signature . "(*error* string)")
           (arguments . (("string" . "Type: String\nA textual string that contains a description of the error and is passed by AutoCAD.")))
           (return-values . "Type: N/A\nThis function does not return, except when using vl-exit-with-value.")
           (release-information . nil)
           (history . nil)
           (examples . "The following function does the same thing that the AutoLISP standard error handler does. It prints the text “error: ” followed by a description:\n\n(defun *error* (msg)\n  (princ \"error: \")\n  (princ msg)\n (princ)\n)")
           (url . "https://help.autodesk.com/cloudhelp/2023/ENU/AutoCAD-AutoLISP-Reference/files/GUID-CF913180-17CC-43C7-B89F-3BC82FFBEFB9.htm")
           (guid . "GUID-CF913180-17CC-43C7-B89F-3BC82FFBEFB9"))))
    *autolisp-reference-parts*))

(setq *autolisp-reference-entry* nil)

(setq *autolisp-reference-value* "GUID-60AFEFAD-1DF5-448F-A2E9-D7260DB279E4")

(setq *autolisp-reference-entry* (cons (cons 'guid *autolisp-reference-value*) *autolisp-reference-entry*))

(setq *autolisp-reference-value* "https://help.autodesk.com/cloudhelp/2023/ENU/AutoCAD-AutoLISP-Reference/files/GUID-60AFEFAD-1DF5-448F-A2E9-D7260DB279E4.htm")

(setq *autolisp-reference-entry* (cons (cons 'url *autolisp-reference-value*) *autolisp-reference-entry*))

(setq *autolisp-reference-value* "The following example demonstrates the use of the *pop-error-mode* function.\n\n(defun my_err (err_msg)\n    (if (/= err_msg \"Function cancelled\")\n      (prompt (strcat \"\\nError: \" err_msg))\n    )\n    (command \"._undo\" \"_e\")\n    (command \"._U\")\n    (setq *error* olderr)\n  (princ)\n)\n\n(defun myUtil (key / )\n    (setq olderr *error*\n          *error* my_err)\n    (*push-error-using-command*)         ; Indicate use of the command function instead of command-s\n                                         ; in a custom error handler\n\n    (command \"._undo\" \"_group\")          ; The following will not be executed in this sample, but is good\n                                         ; framework for setting up your own error handlers\n\n    (/ 1 0)                              ; Call a function with incorrect values to trigger the custom error handler\n                     ")

(setq *autolisp-reference-value* (strcat *autolisp-reference-value* "                    ; Remove when setting up your code\n\n    ;; Perform your tasks here\n\n    (command \"._undo\" \"_e\")\n    (setq *error* olderr)                ; Restore old *error* handler\n    (*pop-error-mode*)                   ; End the use of *push-error-using-command*\n)\n\nAfter loading the sample code, enter (myutil “String”) at the Command prompt to enter the error handler."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T\nA value of T is returned.")

(setq *autolisp-reference-entry* (cons (cons 'return-values *autolisp-reference-value*) *autolisp-reference-entry*))

(setq *autolisp-reference-value* nil)

(setq *autolisp-reference-entry* (cons (cons 'arguments *autolisp-reference-value*) *autolisp-reference-entry*))

(setq *autolisp-reference-value* "(*pop-error-mode*)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Error-Handling"))

(setq *autolisp-reference-entry* (cons (cons 'feature-groups *autolisp-reference-value*) *autolisp-reference-entry*))

(setq *autolisp-reference-value* "Non-alphabetic")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Error-handling function that ends the previous call to *push-error-using-command* or *push-error-using-stack*")

(setq *autolisp-reference-entry* (cons (cons 'summary *autolisp-reference-value*) *autolisp-reference-entry*))

(setq *autolisp-reference-value* "*pop-error-mode* (AutoLISP)")

(setq *autolisp-reference-entry* (cons (cons 'title *autolisp-reference-value*) *autolisp-reference-entry*))

(setq *autolisp-reference-value* "*pop-error-mode*")

(setq *autolisp-reference-entry* (cons (cons 'name *autolisp-reference-value*) *autolisp-reference-entry*))

(setq *autolisp-reference-parts* (cons (list (cons "*pop-error-mode*" *autolisp-reference-entry*)) *autolisp-reference-parts*))

(setq *autolisp-reference-entry* nil)

(setq *autolisp-reference-value* "GUID-620E034A-9151-427F-B6F5-B360D14DA925")

(setq *autolisp-reference-entry* (cons (cons 'guid *autolisp-reference-value*) *autolisp-reference-entry*))

(setq *autolisp-reference-value* "https://help.autodesk.com/cloudhelp/2023/ENU/AutoCAD-AutoLISP-Reference/files/GUID-620E034A-9151-427F-B6F5-B360D14DA925.htm")

(setq *autolisp-reference-entry* (cons (cons 'url *autolisp-reference-value*) *autolisp-reference-entry*))

(setq *autolisp-reference-value* "The following example demonstrates the use of the *push-error-using-command* function.\n\n(defun my_err (err_msg)\n    (if (/= err_msg \"Function cancelled\")\n      (prompt (strcat \"\\nError: \" err_msg))\n    )\n    (command \"._undo\" \"_e\")\n    (command \"._U\")\n    (setq *error* olderr)\n  (princ)\n)\n\n(defun myUtil (key / )\n    (setq olderr *error*\n              *error* my_err)\n    (*push-error-using-command*)         ; Indicate use of Command function instead of Command-s\n                                         ; in the custom error handler\n\n    (command \"._undo\" \"_group\")          ; The following will not be executed in this sample, but is good\n                                         ; framework for setting up your own error handlers\n\n    (/ 1 0)                              ; Call a function with incorrect values to trigger the custom error handler\n         ")

(setq *autolisp-reference-value* (strcat *autolisp-reference-value* "                                ; Remove when setting up your code\n\n    ;; Perform your tasks here\n\n    (command \"._undo\" \"_e\")\n    (setq *error* olderr)                ; Restore old *error* handler\n    (*pop-error-mode*)                   ; End the use of *push-error-using-command*\n)\n\nAfter loading the sample code, enter (myutil “String”) at the Command prompt to enter the error handler."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T\nA value of T is returned.")

(setq *autolisp-reference-entry* (cons (cons 'return-values *autolisp-reference-value*) *autolisp-reference-entry*))

(setq *autolisp-reference-value* nil)

(setq *autolisp-reference-entry* (cons (cons 'arguments *autolisp-reference-value*) *autolisp-reference-entry*))

(setq *autolisp-reference-value* "(*push-error-using-command*)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Error-Handling"))

(setq *autolisp-reference-entry* (cons (cons 'feature-groups *autolisp-reference-value*) *autolisp-reference-entry*))

(setq *autolisp-reference-value* nil)

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Error-handling function that indicates the use of the command function within a custom *error* handler")

(setq *autolisp-reference-entry* (cons (cons 'summary *autolisp-reference-value*) *autolisp-reference-entry*))

(setq *autolisp-reference-value* "*push-error-using-command* (AutoLISP)")

(setq *autolisp-reference-entry* (cons (cons 'title *autolisp-reference-value*) *autolisp-reference-entry*))

(setq *autolisp-reference-value* "*push-error-using-command*")

(setq *autolisp-reference-entry* (cons (cons 'name *autolisp-reference-value*) *autolisp-reference-entry*))

(setq *autolisp-reference-parts* (cons (list (cons "*push-error-using-command*" *autolisp-reference-entry*)) *autolisp-reference-parts*))

(setq *autolisp-reference-entry* nil)

(setq *autolisp-reference-value* "GUID-C28420C9-2210-4EEC-AA73-2962999D1BC1")

(setq *autolisp-reference-entry* (cons (cons 'guid *autolisp-reference-value*) *autolisp-reference-entry*))

(setq *autolisp-reference-value* "https://help.autodesk.com/cloudhelp/2023/ENU/AutoCAD-AutoLISP-Reference/files/GUID-C28420C9-2210-4EEC-AA73-2962999D1BC1.htm")

(setq *autolisp-reference-entry* (cons (cons 'url *autolisp-reference-value*) *autolisp-reference-entry*))

(setq *autolisp-reference-value* "The following example demonstrates the use of the *push-error-using-stack* function.\n\n(setq var1 \"Global1\"      ; Set some global variables\n      var2 \"Global2\")\n\n(defun mySub_err (err_msg)\n    (if (/= err_msg \"Function cancelled\")\n      (progn\n        (prompt (strcat \"\\nError: \" err_msg))\n        (prompt (strcat \"\\nLocalSub1: \" var1))\n        (prompt (strcat \"\\nLocalSub2: \" var2))\n        (terpri)\n      )\n    )\n\n    (command-s \"._undo\" \"_e\")\n    (command-s \"._U\")\n    (setq *error* olderr)\n  (princ)\n)\n\n(defun subUtil (val / olderr var1 var2)\n    (*push-error-using-stack*)         ; Indicates if the custom error handler has access to local\n                                       ; variables defined in his function\n\n    (setq olderr *error*\n          *error* mySub_err)\n\n    (command \"._undo\" \"_group\")        ; The following will not be ex")

(setq *autolisp-reference-value* (strcat *autolisp-reference-value* "ecuted in this sample, but is good\n                                       ; framework for setting up your own error handlers\n\n    (setq var1 \"Sub1\"                  ; Set some local variables\n          var2 \"Sub2\")\n\n    ;; Perform your tasks here\n    (strcat \"Foo\" val)\n\n    (command \"._undo\" \"_e\")\n    (setq *error* olderr)              ; Restore old *error* handler\n    (*pop-error-mode*)                 ; End the use of *push-error-using-command*\n)\n\n(defun my_err (err_msg)\n    (if (/= err_msg \"Function cancelled\")\n      (progn\n        (prompt (strcat \"\\nError: \" err_msg))\n        (prompt (strcat \"\\nLocal1: \" var1))\n        (prompt (strcat \"\\nLocal2: \" var2))\n        (terpri)\n      )\n    )\n\n    (command \"._undo\" \"_e\")\n    (command \"._U\")\n    (setq *error* olderr)\n  (princ)\n)\n\n(defun myUtil (val / var1 var2)\n    (setq olderr *error*"))

(setq *autolisp-reference-value* (strcat *autolisp-reference-value* "\n          *error* my_err)\n\n    (*push-error-using-command*)       ; Indicate use of Command function instead of Command-s\n                                       ; in the custom error handler\n\n    (setq var1 \"Local1\"                ; Set some local variables\n          var2 \"Local2\")\n\n    (command \"._undo\" \"_group\")        ; The following will not be executed in this sample, but is good\n                                       ; framework for setting up your own error handlers\n\n    (subUtil val)                      ; Call to a custom function that uses *push-error-using-stack*\n\n    (/ 1 0)                            ; Call a function with incorrect values to trigger the custom error handler\n                                       ; Remove when setting up your code\n\n    ;; Perform your tasks here\n\n    (command \"._undo\" \"_e\")\n    (setq *error* olderr)          "))

(setq *autolisp-reference-value* (strcat *autolisp-reference-value* "    ; Restore old *error* handler\n    (*pop-error-mode*)                 ; End the use of *push-error-using-command*\n)\n\nAfter loading the sample code, enter (myutil 1) at the Command prompt to enter the error handler for the nested function and (myutil “String”) to test the error handler of the main function."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T\nA value of T is returned.")

(setq *autolisp-reference-entry* (cons (cons 'return-values *autolisp-reference-value*) *autolisp-reference-entry*))

(setq *autolisp-reference-value* nil)

(setq *autolisp-reference-entry* (cons (cons 'arguments *autolisp-reference-value*) *autolisp-reference-entry*))

(setq *autolisp-reference-value* "(*push-error-using-stack*)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Error-Handling"))

(setq *autolisp-reference-entry* (cons (cons 'feature-groups *autolisp-reference-value*) *autolisp-reference-entry*))

(setq *autolisp-reference-value* "Non-alphabetic")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Error-handling function that indicates the use of variables from the AutoLISP stack within a custom *error* handler")

(setq *autolisp-reference-entry* (cons (cons 'summary *autolisp-reference-value*) *autolisp-reference-entry*))

(setq *autolisp-reference-value* "*push-error-using-stack* (AutoLISP)")

(setq *autolisp-reference-entry* (cons (cons 'title *autolisp-reference-value*) *autolisp-reference-entry*))

(setq *autolisp-reference-value* "*push-error-using-stack*")

(setq *autolisp-reference-entry* (cons (cons 'name *autolisp-reference-value*) *autolisp-reference-entry*))

(setq *autolisp-reference-parts* (cons (list (cons "*push-error-using-stack*" *autolisp-reference-entry*)) *autolisp-reference-parts*))

(setq *autolisp-reference-parts*
  (cons
    '(("+" .
          ((name . "+")
           (title . "+ (add) (AutoLISP)")
           (summary . "Returns the sum of all numbers")
           (source-kind . "AutoLISP")
           (alphabetic-group . "Non-alphabetic")
           (feature-groups . ("Arithmetic"))
           (supported-platforms . "Windows and Mac OS")
           (signature . "(+ [number number ...])")
           (arguments . (("number" . "Type: Integer or Real\nA numeric value.")))
           (return-values . "Type: Integer or Real\nThe result of the addition. If you supply only one number argument, this function returns the result of adding it to zero. If you supply no arguments, the function returns 0.")
           (release-information . nil)
           (history . nil)
           (examples . "(+ 1 2)\n3\n\n(+ 1 2 3 4.5)\n10.5\n\n(+ 1 2 3 4.0)\n10.0")
           (url . "https://help.autodesk.com/cloudhelp/2023/ENU/AutoCAD-AutoLISP-Reference/files/GUID-FCD1F559-F9EA-49F3-AE53-8FF7D90B3B4C.htm")
           (guid . "GUID-FCD1F559-F9EA-49F3-AE53-8FF7D90B3B4C"))))
    *autolisp-reference-parts*))

(setq *autolisp-reference-parts*
  (cons
    '(("-" .
          ((name . "-")
           (title . "- (subtract) (AutoLISP)")
           (summary . "Subtracts the second and following numbers from the first and returns the difference")
           (source-kind . "AutoLISP")
           (alphabetic-group . "Non-alphabetic")
           (feature-groups . ("Arithmetic"))
           (supported-platforms . "Windows and Mac OS")
           (signature . "(- [number number ...])")
           (arguments . (("number" . "Type: Integer or Real\nA numeric value.")))
           (return-values . "Type: Integer or Real\nThe result of the subtraction. If you supply more than two number arguments, this function returns the result of subtracting the sum of the second through the last numbers from the first number. If you supply only one number argument, this function subtracts the number from zero, and returns a negative number. Supplying no arguments returns 0.")
           (release-information . nil)
           (history . nil)
           (examples . "(- 50 40)\n10\n\n(- 50 40.0)\n10.0\n\n(- 50 40.0 2.5)\n7.5\n\n(- 8)\n-8")
           (url . "https://help.autodesk.com/cloudhelp/2023/ENU/AutoCAD-AutoLISP-Reference/files/GUID-53A08CC7-131C-4C7C-B1DA-653559D49E4F.htm")
           (guid . "GUID-53A08CC7-131C-4C7C-B1DA-653559D49E4F"))))
    *autolisp-reference-parts*))

(setq *autolisp-reference-parts*
  (cons
    '(("/" .
          ((name . "/")
           (title . "/ (divide) (AutoLISP)")
           (summary . "Divides the first number by the product of the remaining numbers and returns the quotient")
           (source-kind . "AutoLISP")
           (alphabetic-group . "Non-alphabetic")
           (feature-groups . ("Arithmetic"))
           (supported-platforms . "Windows and Mac OS")
           (signature . "(/ [number number ...])")
           (arguments . (("number" . "Type: Integer or Real\nA numeric value.")))
           (return-values . "Type: Integer or Real\nThe result of the division. If you supply more than two number arguments, this function divides the first number by the product of the second through the last numbers, and returns the final quotient. If you supply one number argument, this function returns the result of dividing it by one; it returns the number. Supplying no arguments returns 0.")
           (release-information . nil)
           (history . nil)
           (examples . "(/ 100 2)\n50\n\n(/ 100 2.0)\n50.0\n\n(/ 100 20.0 2)\n2.5\n\n(/ 100 20 2)\n2\n\n(/ 4)\n4")
           (url . "https://help.autodesk.com/cloudhelp/2023/ENU/AutoCAD-AutoLISP-Reference/files/GUID-E9E70DA9-6048-470D-B899-239B097671D2.htm")
           (guid . "GUID-E9E70DA9-6048-470D-B899-239B097671D2"))))
    *autolisp-reference-parts*))

(setq *autolisp-reference-parts*
  (cons
    '(("/=" .
          ((name . "/=")
           (title . "/= (not Equal to) (AutoLISP)")
           (summary . "Compares arguments for numerical inequality")
           (source-kind . "AutoLISP")
           (alphabetic-group . "Non-alphabetic")
           (feature-groups . ("Equality and Conditional"))
           (supported-platforms . "Windows and Mac OS")
           (signature . "(/= numstr [numstr ...])")
           (arguments . (("numstr" . "Type: Integer, Real, or String\nA number or string.")))
           (return-values . "Type: T or nil\nT, if no two successive arguments are the same in value; otherwise nil. If only one argument is supplied, T is returned.\nNote: The behavior of /= does not quite conform to other LISP dialects. The standard behavior is to return T if no two arguments in the list have the same value. In AutoLISP, /= returns T if no successive arguments have the same value; see the examples that follow.")
           (release-information . nil)
           (history . nil)
           (examples . "(/= 10 20)\nT\n\n(/= \"you\" \"you\")\nnil\n\n(/= 5.43 5.44)\nT\n\n(/= 10 20 10 20 20)\nnil\n\n(/= 10 20 10 20)\nT")
           (url . "https://help.autodesk.com/cloudhelp/2023/ENU/AutoCAD-AutoLISP-Reference/files/GUID-AA577C72-FC8C-4697-87F6-FF5CB2F0CBC5.htm")
           (guid . "GUID-AA577C72-FC8C-4697-87F6-FF5CB2F0CBC5"))))
    *autolisp-reference-parts*))

(setq *autolisp-reference-parts*
  (cons
    '(("1+" .
          ((name . "1+")
           (title . "1+ (increment) (AutoLISP)")
           (summary . "Increments a number by 1")
           (source-kind . "AutoLISP")
           (alphabetic-group . "Non-alphabetic")
           (feature-groups . ("Arithmetic"))
           (supported-platforms . "Windows and Mac OS")
           (signature . "(1+ number)")
           (arguments . (("number" . "Type: Integer or Real\nA numeric value.")))
           (return-values . "Type: Integer or Real\nThe number argument, increased by 1.")
           (release-information . nil)
           (history . nil)
           (examples . "(1+ 5)\n6\n\n(1+ -17.5)\n-16.5")
           (url . "https://help.autodesk.com/cloudhelp/2023/ENU/AutoCAD-AutoLISP-Reference/files/GUID-EF06615A-5BE5-4A86-96CF-643B0712E43A.htm")
           (guid . "GUID-EF06615A-5BE5-4A86-96CF-643B0712E43A"))))
    *autolisp-reference-parts*))

(setq *autolisp-reference-parts*
  (cons
    '(("1-" .
          ((name . "1-")
           (title . "1- (decrement) (AutoLISP)")
           (summary . "Decrements a number by 1")
           (source-kind . "AutoLISP")
           (alphabetic-group . "Non-alphabetic")
           (feature-groups . ("Arithmetic"))
           (supported-platforms . "Windows and Mac OS")
           (signature . "(1- number)")
           (arguments . (("number" . "Type: Integer or Real\nA numeric value.")))
           (return-values . "Type: Integer or Real\nThe number argument, reduced by 1.")
           (release-information . nil)
           (history . nil)
           (examples . "(1- 5)\n4\n\n(1- -17.5)\n-18.5")
           (url . "https://help.autodesk.com/cloudhelp/2023/ENU/AutoCAD-AutoLISP-Reference/files/GUID-4E3A882A-959D-4B46-BA5E-5A3C1BDB3079.htm")
           (guid . "GUID-4E3A882A-959D-4B46-BA5E-5A3C1BDB3079"))))
    *autolisp-reference-parts*))

(setq *autolisp-reference-parts*
  (cons
    '(("<" .
          ((name . "<")
           (title . "< (less than) (AutoLISP)")
           (summary . "Returns T if each argument is numerically less than the argument to its right; otherwise nil")
           (source-kind . "AutoLISP")
           (alphabetic-group . "Non-alphabetic")
           (feature-groups . ("Equality and Conditional"))
           (supported-platforms . "Windows and Mac OS")
           (signature . "(< numstr [numstr ...])")
           (arguments . (("numstr" . "Type: Integer, Real, or String\nA number or string.")))
           (return-values . "Type: T or nil\nT, if each argument is numerically less than the argument to its right; otherwise returns nil . If only one argument is supplied, T is returned.")
           (release-information . nil)
           (history . nil)
           (examples . "(< 10 20)\nT\n\n(< \"b\" \"c\")\nT\n\n(< 357 33.2)\nnil\n\n(< 2 3 88)\nT\n\n(< 2 3 4 4)\nnil")
           (url . "https://help.autodesk.com/cloudhelp/2023/ENU/AutoCAD-AutoLISP-Reference/files/GUID-67C8900F-0491-4D91-AA05-9136639E7424.htm")
           (guid . "GUID-67C8900F-0491-4D91-AA05-9136639E7424"))))
    *autolisp-reference-parts*))

(setq *autolisp-reference-parts*
  (cons
    '(("<=" .
          ((name . "<=")
           (title . "<= (less than or equal to) (AutoLISP)")
           (summary . "Returns T if each argument is numerically less than or equal to the argument to its right; otherwise returns nil")
           (source-kind . "AutoLISP")
           (alphabetic-group . "Non-alphabetic")
           (feature-groups . ("Equality and Conditional"))
           (supported-platforms . "Windows and Mac OS")
           (signature . "(<= numstr [numstr ...])")
           (arguments . (("numstr" . "Type: Integer, Real, or String\nA number or string.")))
           (return-values . "Type: T or nil\nT, if each argument is numerically less than or equal to the argument to its right; otherwise returns nil. If only one argument is supplied, T is returned.")
           (release-information . nil)
           (history . nil)
           (examples . "(<= 10 20)\nT\n\n(<= \"b\" \"b\")\nT\n\n(<= 357 33.2)\nnil\n\n(<= 2 9 9)\nT\n\n(<= 2 9 4 5)\nnil")
           (url . "https://help.autodesk.com/cloudhelp/2023/ENU/AutoCAD-AutoLISP-Reference/files/GUID-66B7B146-E279-4C22-9C0A-1F312166C15B.htm")
           (guid . "GUID-66B7B146-E279-4C22-9C0A-1F312166C15B"))))
    *autolisp-reference-parts*))

(setq *autolisp-reference-parts*
  (cons
    '(("=" .
          ((name . "=")
           (title . "= (equal to) (AutoLISP)")
           (summary . "Compares arguments for numerical equality")
           (source-kind . "AutoLISP")
           (alphabetic-group . "Non-alphabetic")
           (feature-groups . ("Equality and Conditional"))
           (supported-platforms . "Windows and Mac OS")
           (signature . "(= numstr [numstr ...])")
           (arguments . (("numstr" . "Type: Integer, Real, or String\nA number or string.")))
           (return-values . "Type: T or nil\nT, if all arguments are numerically equal; otherwise nil. If only one argument is supplied, T is returned.")
           (release-information . nil)
           (history . nil)
           (examples . "(= 4 4.0)\nT\n\n(= 20 388)\nnil\n\n(= 2.4 2.4 2.4)\nT\n\n(= 499 499 500)\nnil\n\n(= \"me\" \"me\")\nT\n\n(= \"me\" \"you\")\nnil")
           (url . "https://help.autodesk.com/cloudhelp/2023/ENU/AutoCAD-AutoLISP-Reference/files/GUID-3F1959A8-AEC4-47C5-8E9E-80364BCA93B2.htm")
           (guid . "GUID-3F1959A8-AEC4-47C5-8E9E-80364BCA93B2"))))
    *autolisp-reference-parts*))

(setq *autolisp-reference-parts*
  (cons
    '((">" .
          ((name . ">")
           (title . "> (greater than) (AutoLISP)")
           (summary . "Returns T if each argument is numerically greater than the argument to its right; otherwise returns nil")
           (source-kind . "AutoLISP")
           (alphabetic-group . "Non-alphabetic")
           (feature-groups . ("Equality and Conditional"))
           (supported-platforms . "Windows and Mac OS")
           (signature . "(> numstr [numstr ...])")
           (arguments . (("numstr" . "Type: Integer, Real, or String\nA number or string.")))
           (return-values . "Type: T or nil\nT, if each argument is numerically greater than the argument to its right; otherwise nil. If only one argument is supplied, T is returned.")
           (release-information . nil)
           (history . nil)
           (examples . "(> 120 17)\nT\n\n(> \"c\" \"b\")\nT\n\n(> 3.5 1792)\nnil\n\n(> 77 4 2)\nT\n\n(> 77 4 4)\nnil")
           (url . "https://help.autodesk.com/cloudhelp/2023/ENU/AutoCAD-AutoLISP-Reference/files/GUID-DAB2660E-AB9D-425D-B0C5-C5774164ADCD.htm")
           (guid . "GUID-DAB2660E-AB9D-425D-B0C5-C5774164ADCD"))))
    *autolisp-reference-parts*))

(setq *autolisp-reference-parts*
  (cons
    '((">=" .
          ((name . ">=")
           (title . ">= (greater than or equal to) (AutoLISP)")
           (summary . "Returns T if each argument is numerically greater than or equal to the argument to its right; otherwise returns nil")
           (source-kind . "AutoLISP")
           (alphabetic-group . "Non-alphabetic")
           (feature-groups . ("Equality and Conditional"))
           (supported-platforms . "Windows and Mac OS")
           (signature . "(>= numstr [numstr ...])")
           (arguments . (("numstr" . "Type: Integer, Real, or String\nA number or string.")))
           (return-values . "Type: T or nil\nT, if each argument is numerically greater than or equal to the argument to its right; otherwise nil. If only one argument is supplied, T is returned.")
           (release-information . nil)
           (history . nil)
           (examples . "(>= 120 17)\nT\n\n(>= \"c\" \"C\")\nT\n\n(>= 3.5 1792)\nnil\n\n(>= 77 4 2)\nT\n\n(>= 77 4 9)\nnil")
           (url . "https://help.autodesk.com/cloudhelp/2023/ENU/AutoCAD-AutoLISP-Reference/files/GUID-586BD9C1-441C-47DE-B6E2-1445518CABBA.htm")
           (guid . "GUID-586BD9C1-441C-47DE-B6E2-1445518CABBA"))))
    *autolisp-reference-parts*))

(setq *autolisp-reference-parts*
  (cons
    '(("abs" .
          ((name . "abs")
           (title . "abs (AutoLISP)")
           (summary . "Returns the absolute value of a number")
           (source-kind . "AutoLISP")
           (alphabetic-group . "A")
           (feature-groups . ("Arithmetic"))
           (supported-platforms . "Windows and Mac OS")
           (signature . "(abs number)")
           (arguments . (("number" . "Type: Integer or Real\nA numeric value.")))
           (return-values . "Type: Integer or Real\nThe absolute value of the number argument.")
           (release-information . nil)
           (history . nil)
           (examples . "(abs 100)\n100\n\n(abs -100)\n100\n\n(abs -99.25)\n99.25")
           (url . "https://help.autodesk.com/cloudhelp/2023/ENU/AutoCAD-AutoLISP-Reference/files/GUID-3AF854D7-9B75-4A4B-ABA4-E47DB90FB2F6.htm")
           (guid . "GUID-3AF854D7-9B75-4A4B-ABA4-E47DB90FB2F6"))))
    *autolisp-reference-parts*))

(setq *autolisp-reference-parts*
  (cons
    '(("acad-pop-dbmod" .
          ((name . "acad-pop-dbmod")
           (title . "acad-pop-dbmod (AutoLISP)")
           (summary . "Restores the value of the DBMOD system variable to the value that was most recently stored with acad-push-dbmod")
           (source-kind . "AutoLISP")
           (alphabetic-group . "A")
           (feature-groups . nil)
           (supported-platforms . "Windows and Mac OS")
           (signature . "(acad-pop-dbmod)")
           (arguments . nil)
           (return-values . "Type: T or nil\nReturns T if successful; otherwise, if the stack is empty, returns nil.")
           (release-information . nil)
           (history . nil)
           (examples . nil)
           (url . "https://help.autodesk.com/cloudhelp/2023/ENU/AutoCAD-AutoLISP-Reference/files/GUID-9C141D94-58CD-4A00-8247-7712CDBE813F.htm")
           (guid . "GUID-9C141D94-58CD-4A00-8247-7712CDBE813F"))))
    *autolisp-reference-parts*))

(setq *autolisp-reference-parts*
  (cons
    '(("acad-push-dbmod" .
          ((name . "acad-push-dbmod")
           (title . "acad-push-dbmod (AutoLISP)")
           (summary . "Stores the current value of the DBMOD system variable")
           (source-kind . "AutoLISP")
           (alphabetic-group . "A")
           (feature-groups . nil)
           (supported-platforms . "Windows and Mac OS")
           (signature . "(acad-push-dbmod)")
           (arguments . nil)
           (return-values . "Type: T\nAlways returns T.")
           (release-information . nil)
           (history . nil)
           (examples . "The following example shows how to store the modification status of a drawing, change the status, and then restore the original status.\n\n(acad-push-dbmod)\n(setq new_line '((0 . \"LINE\") (100 . \"AcDbEntity\") (8 . \"0\")\n             (100 . \"AcDbLine\") (10 1.0 2.0 0.0) (11 2.0 1.0 0.0)\n             (210 0.0 0.0 1.0)))\n(entmake new_line)            ; Set DBMOD to flag 1\n(command \"._color\" \"2\")        ; Set DBMOD to flag 4\n(command \"._-vports\" \"_SI\")    ; Set DBMOD to flag 8\n(command \"._vpoint\" \"0,0,1\")   ; Set DBMOD to flag 16\n(acad-pop-dbmod)              ; Set DBMOD to original value")
           (url . "https://help.autodesk.com/cloudhelp/2023/ENU/AutoCAD-AutoLISP-Reference/files/GUID-1B34A525-A881-42A8-BD07-865CA685F33B.htm")
           (guid . "GUID-1B34A525-A881-42A8-BD07-865CA685F33B"))))
    *autolisp-reference-parts*))

(setq *autolisp-reference-parts*
  (cons
    '(("acad_colordlg" .
          ((name . "acad_colordlg")
           (title . "acad_colordlg (AutoLISP)")
           (summary . "Displays the standard AutoCAD color selection dialog box")
           (source-kind . "AutoLISP")
           (alphabetic-group . "A")
           (feature-groups . ("Query and Command"))
           (supported-platforms . "Windows only")
           (signature . "(acad_colordlg colornum [flag])")
           (arguments . (("colornum" . "Type: Integer\nAn integer in the range 0-256 (inclusive), specifying the AutoCAD color number to display as the initial default.\nA colornum value of 0 defaults to ByBlock, and a value of 256 defaults to ByLayer.")
                           ("flag" . "Type: T or nil\nIf set to nil, disables the ByLayer and ByBlock buttons. Omitting the flag argument or setting it to a non-nil value enables the ByLayer and ByBlock buttons.")))
           (return-values . "Type: Integer or nil\nThe user-selected color number; otherwise nil, if the user cancels the dialog box.")
           (release-information . nil)
           (history . nil)
           (examples . "Prompt the user to select a color, and default to green if none is selected:\n\n(acad_colordlg 3)")
           (url . "https://help.autodesk.com/cloudhelp/2023/ENU/AutoCAD-AutoLISP-Reference/files/GUID-5E2A5569-02F4-496B-9CD7-E2457305FF35.htm")
           (guid . "GUID-5E2A5569-02F4-496B-9CD7-E2457305FF35"))))
    *autolisp-reference-parts*))

(setq *autolisp-reference-parts*
  (cons
    '(("acad_helpdlg" .
          ((name . "acad_helpdlg")
           (title . "acad_helpdlg (AutoLISP)")
           (summary . "Invokes the help facility (obsolete)")
           (source-kind . "AutoLISP")
           (alphabetic-group . "A")
           (feature-groups . ("Query and Command"))
           (supported-platforms . "Windows only")
           (signature . "(acad_helpdlg helpfile topic)")
           (arguments . (("helpfile" . "Type: String\nThe path and file name of the help file to open.")
                           ("topic" . "Type: String\nThe name of the topic to display in the help file.")))
           (return-values . "Type: String or nil\nReturns the file name of the help file if it is found; otherwise, nil is returned if the file is not found.")
           (release-information . nil)
           (history . nil)
           (examples . nil)
           (url . "https://help.autodesk.com/cloudhelp/2023/ENU/AutoCAD-AutoLISP-Reference/files/GUID-23B68C07-57B2-4875-868D-E69C139CE22B.htm")
           (guid . "GUID-23B68C07-57B2-4875-868D-E69C139CE22B"))))
    *autolisp-reference-parts*))

(setq *autolisp-reference-parts*
  (cons
    '(("acad_strlsort" .
          ((name . "acad_strlsort")
           (title . "acad_strlsort (AutoLISP)")
           (summary . "Sorts a list of strings in alphabetical order")
           (source-kind . "AutoLISP")
           (alphabetic-group . "A")
           (feature-groups . ("List Manipulation"))
           (supported-platforms . "Windows and Mac OS")
           (signature . "(acad_strlsort list)")
           (arguments . (("list" . "Type: List\nThe list of strings to be sorted.")))
           (return-values . "Type: List or nil\nThe list in alphabetical order. If the list is invalid or if there is not enough memory to do the sort, acad_strlsort returns nil.")
           (release-information . nil)
           (history . nil)
           (examples . "Sort a list of abbreviated month names:\n\n(setq mos '(\"Jan\" \"Feb\" \"Mar\" \"Apr\" \"May\" \"Jun\" \"Jul\" \"Aug\" \"Sep\" \"Oct\" \"Nov\" \"Dec\"))\n(\"Jan\" \"Feb\" \"Mar\" \"Apr\" \"May\" \"Jun\" \"Jul\" \"Aug\" \"Sep\" \"Oct\" \"Nov\" \"Dec\")\n\n(acad_strlsort mos)\n(\"Apr\" \"Aug\" \"Dec\" \"Feb\" \"Jan\" \"Jul\" \"Jun\" \"Mar\" \"May\" \"Nov\" \"Oct\" \"Sep\")")
           (url . "https://help.autodesk.com/cloudhelp/2023/ENU/AutoCAD-AutoLISP-Reference/files/GUID-760DDC5B-9D89-4464-B695-9FCC963B5C12.htm")
           (guid . "GUID-760DDC5B-9D89-4464-B695-9FCC963B5C12"))))
    *autolisp-reference-parts*))

(setq *autolisp-reference-entry* nil)

(setq *autolisp-reference-value* "GUID-47F4C7F1-769B-4AA4-8AE9-C81C1C4D6FB9")

(setq *autolisp-reference-entry* (cons (cons 'guid *autolisp-reference-value*) *autolisp-reference-entry*))

(setq *autolisp-reference-value* "https://help.autodesk.com/cloudhelp/2023/ENU/AutoCAD-AutoLISP-Reference/files/GUID-47F4C7F1-769B-4AA4-8AE9-C81C1C4D6FB9.htm")

(setq *autolisp-reference-entry* (cons (cons 'url *autolisp-reference-value*) *autolisp-reference-entry*))

(setq *autolisp-reference-value* "Prompt for a color selection at the command line with a purple color index default selection and alternative text for the command prompt:\n\n(acad_truecolorcli '(62 . 215) 1 \"Pick a color\")\n\nNew Color [Truecolor/COlorbook] <215>:\n\n((62 . 256))\n\nPrompt for a color selection at the command line with a yellow color index default selection, then set the color by layer:\n\n(acad_truecolorcli '(62 . 2))\n\nNew Color [Truecolor/COlorbook] <2 (yellow)>: bylayer\n\n((62 . 256))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nWhen the operation is successful, the function returns a list of one or more dotted pairs (depending on the tab on which the color is selected) describing the color selected. The last dotted pair in the list indicates the color selected. The function returns nil if the user cancels the dialog box.\nColor book color\nIf the last item in the returned list is a 430 pair, then the specified color originates from a color book. This returned list will also contain a 420 pair that describes the corresponding true color and a 62 pair that describes the closest matching color index value.\nTrue color\nIf the returned list contains a 420 pair as the last item, then a true color was specified (as “Red,Green,Blue”). The list will also contain a 62 pair that indicates the closest matching color index. No 430 pair will be present.\nColor index\nIf the last item in the list is a 62 p")

(setq *autolisp-reference-value* (strcat *autolisp-reference-value* "air, then a color index was chosen. No other dotted pairs will be present in the returned list."))

(setq *autolisp-reference-entry* (cons (cons 'return-values *autolisp-reference-value*) *autolisp-reference-entry*))

(setq *autolisp-reference-value* nil)

(setq *autolisp-reference-string* "Type: T or nil\nAn optional prompt string. If this string is omitted, the default value is “New color”.")

(setq *autolisp-reference-value* (cons (cons "alternateprompt" *autolisp-reference-string*) *autolisp-reference-value*))

(setq *autolisp-reference-string* "Type: T or nil\nOmitting the allowbylayer argument or setting it to a non-nil value enables entering ByLayer or ByBlock to set the color. If set to nil, an error results if ByLayer or ByBlock is entered.")

(setq *autolisp-reference-value* (cons (cons "allowbylayer" *autolisp-reference-string*) *autolisp-reference-value*))

(setq *autolisp-reference-string* "Type: List\nA dotted pair that describes the default color. The first element of the dotted pair must be one of the color-related DXF group codes (62, 420, or 430); for example, (62 . ColorIndex), (420 . TrueColor), or (430 . \"colorbook$colorname\").")

(setq *autolisp-reference-value* (cons (cons "color" *autolisp-reference-string*) *autolisp-reference-value*))

(setq *autolisp-reference-entry* (cons (cons 'arguments *autolisp-reference-value*) *autolisp-reference-entry*))

(setq *autolisp-reference-value* "(acad_truecolorcli color [allowbylayer] [alternatePrompt])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* nil)

(setq *autolisp-reference-entry* (cons (cons 'feature-groups *autolisp-reference-value*) *autolisp-reference-entry*))

(setq *autolisp-reference-value* "A")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Prompts for colors at the Command prompt")

(setq *autolisp-reference-entry* (cons (cons 'summary *autolisp-reference-value*) *autolisp-reference-entry*))

(setq *autolisp-reference-value* "acad_truecolorcli (AutoLISP)")

(setq *autolisp-reference-entry* (cons (cons 'title *autolisp-reference-value*) *autolisp-reference-entry*))

(setq *autolisp-reference-value* "acad_truecolorcli")

(setq *autolisp-reference-entry* (cons (cons 'name *autolisp-reference-value*) *autolisp-reference-entry*))

(setq *autolisp-reference-parts* (cons (list (cons "acad_truecolorcli" *autolisp-reference-entry*)) *autolisp-reference-parts*))

(setq *autolisp-reference-entry* nil)

(setq *autolisp-reference-value* "GUID-E6FF435F-9E66-4F37-8770-2E3FB87B8E0B")

(setq *autolisp-reference-entry* (cons (cons 'guid *autolisp-reference-value*) *autolisp-reference-entry*))

(setq *autolisp-reference-value* "https://help.autodesk.com/cloudhelp/2023/ENU/AutoCAD-AutoLISP-Reference/files/GUID-E6FF435F-9E66-4F37-8770-2E3FB87B8E0B.htm")

(setq *autolisp-reference-entry* (cons (cons 'url *autolisp-reference-value*) *autolisp-reference-entry*))

(setq *autolisp-reference-value* "Open the color selection dialog to the Color Index tab and accept the purple default selection:\n\n(acad_truecolordlg '(62 . 215))\n((62 . 215))\n\nOpen the color selection dialog to the True Color tab with a green default selection and with the By Layer and By Block buttons disabled:\n\n(acad_truecolordlg '(420 . 2686760) nil)\n((62 . 80) (420 . 2686760))\n\nOpen the color selection dialog to the Color Books tab and accept the mustard default selection:\n\n(acad_truecolordlg '(430 . \"RAL CLASSIC$RAL 1003\"))\n((62 . 40) (420 . 16235019) (430 . \"RAL CLASSIC$RAL 1003\"))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List (Dotted pair) or nil\nWhen the operation is successful, the function returns a list of one or more dotted pairs (depending on the tab on which the color is selected) describing the color selected. The last dotted pair in the list indicates the color selected. The function returns nil if the user cancels the dialog box.\nColor book color\nIf the last item in the returned list is a 430 pair, then the specified color originates from a color book. This returned list will also contain a 420 pair that describes the corresponding true color and a 62 pair that describes the closest matching color index value.\nTrue color\nIf the returned list contains a 420 pair as the last item, then a true color was specified (as “Red,Green,Blue”). The list will also contain a 62 pair that indicates the closest matching color index. No 430 pair will be present.\nColor index\nIf the last item in the ")

(setq *autolisp-reference-value* (strcat *autolisp-reference-value* "list is a 62 pair, then a color index was chosen. No other dotted pairs will be present in the returned list."))

(setq *autolisp-reference-entry* (cons (cons 'return-values *autolisp-reference-value*) *autolisp-reference-entry*))

(setq *autolisp-reference-value* nil)

(setq *autolisp-reference-string* "Type: List (Dotted pair)\nOptional dotted pair in the same form as color that sets the value of the ByLayer/ByBlock color in the dialog.")

(setq *autolisp-reference-value* (cons (cons "currentlayercolor" *autolisp-reference-string*) *autolisp-reference-value*))

(setq *autolisp-reference-string* "Type: T or nil\nIf set to nil, disables the ByLayer and ByBlock buttons. Omitting the allowbylayer argument or setting it to a non-nil value enables the ByLayer and ByBlock buttons.")

(setq *autolisp-reference-value* (cons (cons "allowbylayer" *autolisp-reference-string*) *autolisp-reference-value*))

(setq *autolisp-reference-string* "Type: List (Dotted pair)\nA dotted pair that describes the default color. The first element of the dotted pair must be one of the color-related DXF group codes (62, 420, or 430); for example, (62 . ColorIndex), (420 . TrueColor), or (430 . \"colorbook$colorname\").")

(setq *autolisp-reference-value* (cons (cons "color" *autolisp-reference-string*) *autolisp-reference-value*))

(setq *autolisp-reference-entry* (cons (cons 'arguments *autolisp-reference-value*) *autolisp-reference-entry*))

(setq *autolisp-reference-value* "(acad_truecolordlg color [allowbylayer] [currentlayercolor])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* nil)

(setq *autolisp-reference-entry* (cons (cons 'feature-groups *autolisp-reference-value*) *autolisp-reference-entry*))

(setq *autolisp-reference-value* "A")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Displays the AutoCAD color selection dialog box with tabs for index color, true color, and color books")

(setq *autolisp-reference-entry* (cons (cons 'summary *autolisp-reference-value*) *autolisp-reference-entry*))

(setq *autolisp-reference-value* "acad_truecolordlg (AutoLISP)")

(setq *autolisp-reference-entry* (cons (cons 'title *autolisp-reference-value*) *autolisp-reference-entry*))

(setq *autolisp-reference-value* "acad_truecolordlg")

(setq *autolisp-reference-entry* (cons (cons 'name *autolisp-reference-value*) *autolisp-reference-entry*))

(setq *autolisp-reference-parts* (cons (list (cons "acad_truecolordlg" *autolisp-reference-entry*)) *autolisp-reference-parts*))

(setq *autolisp-reference-parts*
  (cons
    '(("acdimenableupdate" .
          ((name . "acdimenableupdate")
           (title . "acdimenableupdate (AutoLISP)")
           (summary . "Controls the automatic updating of associative dimensions")
           (source-kind . "AutoLISP")
           (alphabetic-group . "A")
           (feature-groups . nil)
           (supported-platforms . "Windows and Mac OS")
           (signature . "(acdimenableupdate flag)")
           (arguments . (("flag" . "Type: T or nil\nControls the automatic updating of associative dimensions when geometry is modified.\nT -- Enable automatic updating of associative dimensions when the geometry is modified.\nnil -- Associative dimensions are not updated (even if the geometry is modified) until the DIMREGEN command is used.")))
           (return-values . "Type: nil\nAlways returns nil.")
           (release-information . nil)
           (history . nil)
           (examples . "Disable the automatic update of associative dimensions in the drawing:\n\n(acdimenableupdate nil)\n\nEnable the automatic update of associative dimensions in the drawing:\n\n(acdimenableupdate T)")
           (url . "https://help.autodesk.com/cloudhelp/2023/ENU/AutoCAD-AutoLISP-Reference/files/GUID-7E10D18A-6FD6-4B20-A981-27FF77C2F042.htm")
           (guid . "GUID-7E10D18A-6FD6-4B20-A981-27FF77C2F042"))))
    *autolisp-reference-parts*))

(setq *autolisp-reference-entry* nil)

(setq *autolisp-reference-value* "GUID-5A7A7482-8EDB-43C3-BDD1-A7AEF45986DE")

(setq *autolisp-reference-entry* (cons (cons 'guid *autolisp-reference-value*) *autolisp-reference-entry*))

(setq *autolisp-reference-value* "https://help.autodesk.com/cloudhelp/2023/ENU/AutoCAD-AutoLISP-Reference/files/GUID-5A7A7482-8EDB-43C3-BDD1-A7AEF45986DE.htm")

(setq *autolisp-reference-entry* (cons (cons 'url *autolisp-reference-value*) *autolisp-reference-entry*))

(setq *autolisp-reference-value* "The following code changes layer 0 to blue, and then makes several additional layer changes between a set of begin and end marks. If you issue the AutoCAD LAYERP command after running this code, layer 0 reverts to blue.\n\n(defun TestLayerP ()\n  ;; Turn LAYERPMODE on, if it is not already\n  (if (not (acet-layerp-mode))\n    (acet-layerp-mode T)\n  )\n\n  ;; Set layer 0 to the color blue\n  (command \"._layer\" \"_color\" \"blue\" \"0\" \"\")\n\n  ;; Set a begin mark\n  (acet-layerp-mark T)\n\n  ;; Issue a series of layer commands, and then set an end mark\n  (command \"._layer\" \"_color\" \"green\" \"0\" \"\")\n  (command \"._layer\" \"_thaw\" \"*\" \"\")\n  (command \"._layer\" \"_unlock\" \"*\" \"\")\n  (command \"._layer\" \"_ltype\" \"hidden\" \"0\" \"\")\n  (command \"._layer\" \"_color\" \"red\" \"0\" \"\")\n\n  ;; Set an end mark\n  (acet-layerp-mark nil)\n (princ)\n)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nT if a begin mark is in effect; otherwise nil.\nIf status is omitted, acet-layerp-mark returns the current mark status for layer settings.")

(setq *autolisp-reference-entry* (cons (cons 'return-values *autolisp-reference-value*) *autolisp-reference-entry*))

(setq *autolisp-reference-value* nil)

(setq *autolisp-reference-string* "Type: T or nil\nT -- sets a begin mark\nnil -- sets an end mark, clearing the begin mark")

(setq *autolisp-reference-value* (cons (cons "status" *autolisp-reference-string*) *autolisp-reference-value*))

(setq *autolisp-reference-entry* (cons (cons 'arguments *autolisp-reference-value*) *autolisp-reference-entry*))

(setq *autolisp-reference-value* "(acet-layerp-mark [status])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* nil)

(setq *autolisp-reference-entry* (cons (cons 'feature-groups *autolisp-reference-value*) *autolisp-reference-entry*))

(setq *autolisp-reference-value* "A")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Places beginning and ending marks for Layer Previous recording")

(setq *autolisp-reference-entry* (cons (cons 'summary *autolisp-reference-value*) *autolisp-reference-entry*))

(setq *autolisp-reference-value* "acet-layerp-mark (AutoLISP)")

(setq *autolisp-reference-entry* (cons (cons 'title *autolisp-reference-value*) *autolisp-reference-entry*))

(setq *autolisp-reference-value* "acet-layerp-mark")

(setq *autolisp-reference-entry* (cons (cons 'name *autolisp-reference-value*) *autolisp-reference-entry*))

(setq *autolisp-reference-parts* (cons (list (cons "acet-layerp-mark" *autolisp-reference-entry*)) *autolisp-reference-parts*))

(setq *autolisp-reference-parts*
  (cons
    '(("acet-layerp-mode" .
          ((name . "acet-layerp-mode")
           (title . "acet-layerp-mode (AutoLISP)")
           (summary . "Queries and sets the LAYERPMODE setting")
           (source-kind . "AutoLISP")
           (alphabetic-group . "A")
           (feature-groups . nil)
           (supported-platforms . "Windows and Mac OS")
           (signature . "(acet-layerp-mode [status])")
           (arguments . (("status" . "Type: T or nil\nT - Turns LAYERPMODE on, enabling layer-change tracking\nnil - Turns LAYERPMODE off\nIf this argument is not present, acet-layerp-mode returns the current status of LAYERPMODE.")))
           (return-values . "Type: T or nil\nT if current status of LAYERPMODE is on; nil if LAYERPMODE is off.")
           (release-information . nil)
           (history . nil)
           (examples . "Check the current status of LAYERPMODE:\n\n(acet-layerp-mode)\nT\n\nTurn LAYERPMODE off:\n\n(acet-layerp-mode nil)\nnil\n\nCheck the current status of LAYERPMODE:\n\n(acet-layerp-mode)\nnil")
           (url . "https://help.autodesk.com/cloudhelp/2023/ENU/AutoCAD-AutoLISP-Reference/files/GUID-6E9FD664-C724-48BA-BFB7-8A28D02B59B5.htm")
           (guid . "GUID-6E9FD664-C724-48BA-BFB7-8A28D02B59B5"))))
    *autolisp-reference-parts*))

(setq *autolisp-reference-parts*
  (cons
    '(("acet-laytrans" .
          ((name . "acet-laytrans")
           (title . "acet-laytrans (AutoLISP)")
           (summary . "Translates drawing layers to standards defined in another drawing or standards file")
           (source-kind . "AutoLISP")
           (alphabetic-group . "A")
           (feature-groups . nil)
           (supported-platforms . "Windows only")
           (signature . "(acet-laytrans filename [settings])")
           (arguments . (("filename" . "Type: String\nA string specifying a file containing layer mappings to be used for translation.")
                           ("settings" . "Type: Integer\nA bit-coded integer specifying Layer Translator processing options. The bits can be added together in any combination to form a value between 0 and 15. If the settings argument is omitted, a value of 15 (all options selected) is assumed. The bit values are as follows:\n0 -- No options\n1 -- Force entity color to BYLAYER\n2 -- Force entity linetype to BYLAYER\n4 -- Translate objects in blocks\n8 -- Write transaction log")))
           (return-values . "Type: T or nil\nT if translation is successful; otherwise nil.")
           (release-information . nil)
           (history . nil)
           (examples . "The following command translates the current drawing using layer mappings saved in LayMap.dwg. No transaction log will be produced, but all other processing options will be in effect.\n\n(acet-laytrans \"c:/my documents/cad drawings/LayMap.dwg\" 7)\nT")
           (url . "https://help.autodesk.com/cloudhelp/2023/ENU/AutoCAD-AutoLISP-Reference/files/GUID-4BD312D1-1850-4DE4-A63D-35367C5F7F5D.htm")
           (guid . "GUID-4BD312D1-1850-4DE4-A63D-35367C5F7F5D"))))
    *autolisp-reference-parts*))

(setq *autolisp-reference-parts*
  (cons
    '(("acet-ms-to-ps" .
          ((name . "acet-ms-to-ps")
           (title . "acet-ms-to-ps (AutoLISP)")
           (summary . "Converts a real value from model space units to paper space units")
           (source-kind . "AutoLISP")
           (alphabetic-group . "A")
           (feature-groups . nil)
           (supported-platforms . "Windows only")
           (signature . "(acet-ms-to-ps [value] [viewport])")
           (arguments . (("value" . "Type: Real\nValue to be converted.")
                           ("viewport" . "Type: Ename (entity name)\nA viewport entity name.")))
           (return-values . "Type: Real or nil\nThe converted real value on success; nil on failure.")
           (release-information . nil)
           (history . nil)
           (examples . "None")
           (url . "https://help.autodesk.com/cloudhelp/2023/ENU/AutoCAD-AutoLISP-Reference/files/GUID-9E316699-FF65-477F-BD28-318FDEC04CC5.htm")
           (guid . "GUID-9E316699-FF65-477F-BD28-318FDEC04CC5"))))
    *autolisp-reference-parts*))

(setq *autolisp-reference-parts*
  (cons
    '(("acet-ps-to-ms" .
          ((name . "acet-ps-to-ms")
           (title . "acet-ps-to-ms (AutoLISP)")
           (summary . "Converts a real value from paper space units to model space units")
           (source-kind . "AutoLISP")
           (alphabetic-group . "A")
           (feature-groups . nil)
           (supported-platforms . "Windows only")
           (signature . "(acet-ps-to-ms [value] [viewport])")
           (arguments . (("value" . "Type: Real\nValue to be converted.")
                           ("viewport" . "Type: Ename (entity name)\nA viewport entity name.")))
           (return-values . "Type: Real or nil\nThe converted real value on success; nil on failure.")
           (release-information . nil)
           (history . nil)
           (examples . "None")
           (url . "https://help.autodesk.com/cloudhelp/2023/ENU/AutoCAD-AutoLISP-Reference/files/GUID-0B38CD6E-1A28-4029-B233-81DB17619F66.htm")
           (guid . "GUID-0B38CD6E-1A28-4029-B233-81DB17619F66"))))
    *autolisp-reference-parts*))

(setq *autolisp-reference-parts*
  (cons
    '(("action_tile" .
          ((name . "action_tile")
           (title . "action_tile (AutoLISP/DCL)")
           (summary . "Assigns an action to evaluate when the user selects the specified tile in a dialog box")
           (source-kind . "AutoLISP/DCL")
           (alphabetic-group . "A")
           (feature-groups . ("Tile- and Attribute-Handling Functions Reference (AutoLISP/DCL)"))
           (supported-platforms . "Windows and Mac OS")
           (signature . "(action_tile key action-expression)")
           (arguments . (("key" . "Type: String\nNames the tile that triggers the action (specified as its key attribute). This argument is case-sensitive.")
                           ("action-expression" . "Type: String\nExpression evaluated when the tile is selected.")))
           (return-values . "Type: T or nil\nT if the key was found; otherwise it returns nil.")
           (release-information . "Releases:\n- AutoCAD R12 and later on Windows\n- AutoCAD 2021 and later on Mac OS")
           (history . nil)
           (examples . "If edit1 is a text box, the action expression in the following action_tile call is evaluated when the user exits the text box:\n\n(action_tile \"edit1\" \"(setq ns $value)\")")
           (url . "https://help.autodesk.com/cloudhelp/2023/ENU/AutoCAD-AutoLISP-Reference/files/GUID-A9E2C14E-1352-4C7B-89F0-C86D3A86B19D.htm")
           (guid . "GUID-A9E2C14E-1352-4C7B-89F0-C86D3A86B19D"))))
    *autolisp-reference-parts*))

(setq *autolisp-reference-parts*
  (cons
    '(("add_list" .
          ((name . "add_list")
           (title . "add_list (AutoLISP/DCL)")
           (summary . "Adds or modifies a string in the currently active dialog box list")
           (source-kind . "AutoLISP/DCL")
           (alphabetic-group . "A")
           (feature-groups . ("List Box and Pop-Up List-Handling Functions Reference (AutoLISP/DCL)"))
           (supported-platforms . "Windows and Mac OS")
           (signature . "(add_list str)")
           (arguments . (("str" . "Type: String\nValue to be assigned to the list.")))
           (return-values . "Type: String or nil\nReturns the string added to the list, if successful; otherwise nil.")
           (release-information . "Releases:\n- AutoCAD R12 and later on Windows\n- AutoCAD 2021 and later on Mac OS")
           (history . nil)
           (examples . "Assuming the currently active DCL file has a popup_list or list_box with a key of longlist, the following code fragment initializes the list and adds to it the text strings in llist.\n\n(setq llist '(\"first line\" \"second line\" \"third line\"))\n(start_list \"longlist\")\n(mapcar 'add_list llist)\n(end_list)\n\nAfter the list has been defined, the following code fragment changes the text in the second line to \"2nd line\".\n\n(start_list \"longlist\" 1 0)\n(add_list \"2nd line\")\n(end_list)")
           (url . "https://help.autodesk.com/cloudhelp/2023/ENU/AutoCAD-AutoLISP-Reference/files/GUID-9BF538FC-BB15-4843-9796-DDCDB6D38C8E.htm")
           (guid . "GUID-9BF538FC-BB15-4843-9796-DDCDB6D38C8E"))))
    *autolisp-reference-parts*))

(setq *autolisp-reference-parts*
  (cons
    '(("alert" .
          ((name . "alert")
           (title . "alert (AutoLISP)")
           (summary . "Displays a dialog box containing an error or warning message")
           (source-kind . "AutoLISP")
           (alphabetic-group . "A")
           (feature-groups . ("Error-Handling"))
           (supported-platforms . "Windows and Mac OS")
           (signature . "(alert msg)")
           (arguments . (("msg" . "Type: String\nThe message to display in the alert box.")))
           (return-values . "Type: nil\nAlways returns nil.")
           (release-information . nil)
           (history . nil)
           (examples . "Display a message in an alert box:\n\n(alert \"That function is not available.\")\n\nDisplay a multiple line message, by using the newline character in string:\n\n(alert \"That function\\nis not available.\")")
           (url . "https://help.autodesk.com/cloudhelp/2023/ENU/AutoCAD-AutoLISP-Reference/files/GUID-1BBC35EB-232F-4593-8B70-D9C473B7BC05.htm")
           (guid . "GUID-1BBC35EB-232F-4593-8B70-D9C473B7BC05"))))
    *autolisp-reference-parts*))

(setq *autolisp-reference-parts*
  (cons
    '(("alloc" .
          ((name . "alloc")
           (title . "alloc (AutoLISP)")
           (summary . "Sets the size of the segment to be used by the expand function")
           (source-kind . "AutoLISP")
           (alphabetic-group . "A")
           (feature-groups . ("Memory Management"))
           (supported-platforms . "Windows and Mac OS")
           (signature . "(alloc n-alloc)")
           (arguments . (("n-alloc" . "Type: Integer\nA number indicating the amount of memory to be allocated. The integer represents the number of symbols, strings, usubrs, reals, and cons cells.")))
           (return-values . "Type: Integer\nThe previous setting of n-alloc.")
           (release-information . nil)
           (history . nil)
           (examples . "(alloc 100)\n1000")
           (url . "https://help.autodesk.com/cloudhelp/2023/ENU/AutoCAD-AutoLISP-Reference/files/GUID-DBC72668-153D-48F4-9C19-87053975A97C.htm")
           (guid . "GUID-DBC72668-153D-48F4-9C19-87053975A97C"))))
    *autolisp-reference-parts*))

(setq *autolisp-reference-parts*
  (cons
    '(("and" .
          ((name . "and")
           (title . "and (AutoLISP)")
           (summary . "Returns the logical AND of the supplied arguments")
           (source-kind . "AutoLISP")
           (alphabetic-group . "A")
           (feature-groups . ("Equality and Conditional"))
           (supported-platforms . "Windows and Mac OS")
           (signature . "(and [expr ...])")
           (arguments . (("expr" . "Type: Symbol, Integer, Real, String, T, or nil\nAny expression.")))
           (return-values . "Type: T or nil\nnil, if any of the expressions evaluate to nil; otherwise T. If and is issued without arguments, it returns T.")
           (release-information . nil)
           (history . nil)
           (examples . "(setq a 103 b nil c \"string\")\n\"string\"\n\n(and 1.4 a c)\nT\n\n(and 1.4 a b c)\nnil")
           (url . "https://help.autodesk.com/cloudhelp/2023/ENU/AutoCAD-AutoLISP-Reference/files/GUID-59FC3712-44E9-4D09-A611-5B153A26AE5E.htm")
           (guid . "GUID-59FC3712-44E9-4D09-A611-5B153A26AE5E"))))
    *autolisp-reference-parts*))

(setq *autolisp-reference-parts*
  (cons
    '(("angle" .
          ((name . "angle")
           (title . "angle (AutoLISP)")
           (summary . "Returns an angle in radians of a line defined by two endpoints")
           (source-kind . "AutoLISP")
           (alphabetic-group . "A")
           (feature-groups . ("Geometric"))
           (supported-platforms . "Windows and Mac OS")
           (signature . "(angle pt1 pt2)")
           (arguments . (("pt1" . "Type: Integer or Real\nAn endpoint.")
                           ("pt2" . "Type: Integer or Real\nAn endpoint.")))
           (return-values . "Type: Real\nAn angle, in radians.\nThe angle is measured from the X axis of the current construction plane, in radians, with angles increasing in the counterclockwise direction. If 3D points are supplied, they are projected onto the current construction plane.")
           (release-information . nil)
           (history . nil)
           (examples . "(angle '(1.0 1.0) '(1.0 4.0))\n1.5708\n\n(angle '(5.0 1.33) '(2.4 1.33))\n3.14159")
           (url . "https://help.autodesk.com/cloudhelp/2023/ENU/AutoCAD-AutoLISP-Reference/files/GUID-F28755D4-E89F-43EF-8E76-40518C7E2728.htm")
           (guid . "GUID-F28755D4-E89F-43EF-8E76-40518C7E2728"))))
    *autolisp-reference-parts*))

(setq *autolisp-reference-parts*
  (cons
    '(("angtof" .
          ((name . "angtof")
           (title . "angtof (AutoLISP)")
           (summary . "Converts a string representing an angle into a real (floating-point) value in radians")
           (source-kind . "AutoLISP")
           (alphabetic-group . "A")
           (feature-groups . ("Conversion"))
           (supported-platforms . "Windows and Mac OS")
           (signature . "(angtof string [units])")
           (arguments . (("string" . "Type: String\nFormatted angular string that angtof can parse correctly to the specified unit. It can be in the same form that angtos returns, or in a form that AutoCAD allows for keyboard entry.")
                           ("units" . "Type: Integer\nSpecifies the units in which the string is formatted. The value should correspond to values allowed for the AutoCAD AUNITS system variable. If unit is omitted, angtof uses the current value of AUNITS. The following units may be specified:\n0 -- Degrees\n1 -- Degrees/minutes/seconds\n2 -- Grads\n3 -- Radians\n4 -- Surveyor's units")))
           (return-values . "Type: Real\nA real value, if successful; otherwise nil.\nThe angtof and angtos functions are complementary: if you pass angtof a string created by angtos, angtof is guaranteed to return a valid value, and vice versa (assuming the unit values match).")
           (release-information . nil)
           (history . nil)
           (examples . "(angtof \"45.0000\")\n0.785398\n\n(angtof \"45.0000\" 3)\n1.0177")
           (url . "https://help.autodesk.com/cloudhelp/2023/ENU/AutoCAD-AutoLISP-Reference/files/GUID-9DE9200B-F27E-4BB6-8AE6-BC5C8A64A527.htm")
           (guid . "GUID-9DE9200B-F27E-4BB6-8AE6-BC5C8A64A527"))))
    *autolisp-reference-parts*))

(setq *autolisp-reference-parts*
  (cons
    '(("angtos" .
          ((name . "angtos")
           (title . "angtos (AutoLISP)")
           (summary . "Converts an angular value in radians into a string")
           (source-kind . "AutoLISP")
           (alphabetic-group . "A")
           (feature-groups . ("Conversion"))
           (supported-platforms . "Windows and Mac OS")
           (signature . "(angtos angle [unit [precision]])")
           (arguments . (("angle" . "Type: Integer or Real\nA number, in radians.")
                           ("unit" . "Type: Integer\nAn integer that specifies the angular units. If unit is omitted, angtos uses the current value of the AutoCAD AUNITS system variable. The following units may be specified:\n0 -- Degrees\n1 -- Degrees/minutes/seconds\n2 -- Grads\n3 -- Radians\n4 -- Surveyor's units")
                           ("precision" . "Type: Integer\nSpecifies the number of decimal places of precision to be returned. If omitted, angtos uses the current setting of the AutoCAD AUPREC system variable.")))
           (return-values . "Type: String or nil\nA string, if successful; otherwise nil.")
           (release-information . nil)
           (history . nil)
           (examples . "(angtos 0.785398 0 4)\n\"45.0000\"\n\n(angtos -0.785398 0 4)\n\"315.0000\"\n\n(angtos -0.785398 4)\n\"S 45d E\"")
           (url . "https://help.autodesk.com/cloudhelp/2023/ENU/AutoCAD-AutoLISP-Reference/files/GUID-C2D277B4-2F59-423F-9C56-E5A1DEFE0CCE.htm")
           (guid . "GUID-C2D277B4-2F59-423F-9C56-E5A1DEFE0CCE"))))
    *autolisp-reference-parts*))

(setq *autolisp-reference-parts*
  (cons
    '(("append" .
          ((name . "append")
           (title . "append (AutoLISP)")
           (summary . "Takes any number of lists and appends them together as one list")
           (source-kind . "AutoLISP")
           (alphabetic-group . "A")
           (feature-groups . ("List Manipulation"))
           (supported-platforms . "Windows and Mac OS")
           (signature . "(append [list ...])")
           (arguments . (("list" . "Type: List\nA list.")))
           (return-values . "Type: List or nil\nA list with all arguments appended to the original. If no arguments are supplied, append returns nil.")
           (release-information . nil)
           (history . nil)
           (examples . "(append '(a b) '(c d))\n(A B C D)\n\n(append '((a)(b)) '((c)(d)))\n((A) (B) (C) (D))")
           (url . "https://help.autodesk.com/cloudhelp/2023/ENU/AutoCAD-AutoLISP-Reference/files/GUID-952B175A-D565-43A4-9208-0E6A27A5E742.htm")
           (guid . "GUID-952B175A-D565-43A4-9208-0E6A27A5E742"))))
    *autolisp-reference-parts*))

(setq *autolisp-reference-parts*
  (cons
    '(("apply" .
          ((name . "apply")
           (title . "apply (AutoLISP)")
           (summary . "Passes a list of arguments to, and executes, a specified function")
           (source-kind . "AutoLISP")
           (alphabetic-group . "A")
           (feature-groups . ("Function-Handling"))
           (supported-platforms . "Windows and Mac OS")
           (signature . "(apply 'function list)")
           (arguments . (("'function" . "Type: Symbol\nA function.\nThe function argument can be either a symbol identifying a defun, or a lambda expression.")
                           ("list" . "Type: List or nil\nA list.\nIf the function accepts no arguments, the value can be nil.")))
           (return-values . "Type: String, Integer, Real, List, T, or nil\nThe result of the function call.")
           (release-information . nil)
           (history . nil)
           (examples . "(apply '+ '(1 2 3))\n6\n\n(apply 'strcat '(\"a\" \"b\" \"c\"))\n\"abc\"")
           (url . "https://help.autodesk.com/cloudhelp/2023/ENU/AutoCAD-AutoLISP-Reference/files/GUID-0574ADA0-0950-456A-9330-A2518421536E.htm")
           (guid . "GUID-0574ADA0-0950-456A-9330-A2518421536E"))))
    *autolisp-reference-parts*))

(setq *autolisp-reference-parts*
  (cons
    '(("arx" .
          ((name . "arx")
           (title . "arx (AutoLISP)")
           (summary . "Returns a list of the currently loaded ObjectARX® applications")
           (source-kind . "AutoLISP")
           (alphabetic-group . "A")
           (feature-groups . ("Application-Handling"))
           (supported-platforms . "Windows and Mac OS")
           (signature . "(arx)")
           (arguments . nil)
           (return-values . "Type: String\nA list of ObjectARX application file names; the path is not included in the file name.")
           (release-information . nil)
           (history . nil)
           (examples . "(arx)\n\nWindows\n\n(\"acapp.arx\" \"acmted.arx\" ...)\n\nMac OS\n\n(\"acapp.bundle\" \"acmted.crx\" ...)")
           (url . "https://help.autodesk.com/cloudhelp/2023/ENU/AutoCAD-AutoLISP-Reference/files/GUID-D74F3A2B-F506-415F-8F5A-258764C2E26D.htm")
           (guid . "GUID-D74F3A2B-F506-415F-8F5A-258764C2E26D"))))
    *autolisp-reference-parts*))

(setq *autolisp-reference-entry* nil)

(setq *autolisp-reference-value* "GUID-965A0D2A-CFD0-4D7C-9D2B-2D8188F0DAC8")

(setq *autolisp-reference-entry* (cons (cons 'guid *autolisp-reference-value*) *autolisp-reference-entry*))

(setq *autolisp-reference-value* "https://help.autodesk.com/cloudhelp/2023/ENU/AutoCAD-AutoLISP-Reference/files/GUID-965A0D2A-CFD0-4D7C-9D2B-2D8188F0DAC8.htm")

(setq *autolisp-reference-entry* (cons (cons 'url *autolisp-reference-value*) *autolisp-reference-entry*))

(setq *autolisp-reference-value* "Load the autoloader.arx file supplied in the AutoCAD installation directory:\n\n(arxload \"<AutoCAD installation directory>/autoloader\")\n\"<AutoCAD installation directory>/autoloader\"")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String\nThe application name, if successful. If unsuccessful and the onfailure argument is supplied, arxload returns the value of this argument; otherwise, failure results in an error message.\nIf you attempt to load an application that is already loaded, arxload issues an error message. You may want to check the currently loaded ObjectARX applications with the arx function before using arxload.")

(setq *autolisp-reference-entry* (cons (cons 'return-values *autolisp-reference-value*) *autolisp-reference-entry*))

(setq *autolisp-reference-value* nil)

(setq *autolisp-reference-string* "Type: String\nAn expression to be executed if the load fails.")

(setq *autolisp-reference-value* (cons (cons "onfailure" *autolisp-reference-string*) *autolisp-reference-value*))

(setq *autolisp-reference-string* "Type: String\nA quoted string or a variable that contains the name of an executable file. You can omit the extension from the file name; .arx (Windows) or .bundle (Mac OS).\nYou must supply the full path name of the ObjectARX executable file, unless the file is in a directory that is in the AutoCAD support file search path.")

(setq *autolisp-reference-value* (cons (cons "application" *autolisp-reference-string*) *autolisp-reference-value*))

(setq *autolisp-reference-entry* (cons (cons 'arguments *autolisp-reference-value*) *autolisp-reference-entry*))

(setq *autolisp-reference-value* "(arxload application [onfailure])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Application-Handling"))

(setq *autolisp-reference-entry* (cons (cons 'feature-groups *autolisp-reference-value*) *autolisp-reference-entry*))

(setq *autolisp-reference-value* "A")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Loads an ObjectARX application")

(setq *autolisp-reference-entry* (cons (cons 'summary *autolisp-reference-value*) *autolisp-reference-entry*))

(setq *autolisp-reference-value* "arxload (AutoLISP)")

(setq *autolisp-reference-entry* (cons (cons 'title *autolisp-reference-value*) *autolisp-reference-entry*))

(setq *autolisp-reference-value* "arxload")

(setq *autolisp-reference-entry* (cons (cons 'name *autolisp-reference-value*) *autolisp-reference-entry*))

(setq *autolisp-reference-parts* (cons (list (cons "arxload" *autolisp-reference-entry*)) *autolisp-reference-parts*))

(setq *autolisp-reference-parts*
  (cons
    '(("arxunload" .
          ((name . "arxunload")
           (title . "arxunload (AutoLISP)")
           (summary . "Unloads an ObjectARX application")
           (source-kind . "AutoLISP")
           (alphabetic-group . "A")
           (feature-groups . ("Application-Handling"))
           (supported-platforms . "Windows and Mac OS")
           (signature . "(arxunload application [onfailure])")
           (arguments . (("application" . "Type: String\nA quoted string or a variable that contains the name of a file that was loaded with the arxload function. You can omit the extension from the file name; .arx (Windows) or .bundle (Mac OS).")
                           ("onfailure" . "Type: String\nAn expression to be executed if the unload fails.")))
           (return-values . "Type: String\nThe application name, if successful. If unsuccessful and the onfailure argument is supplied, arxunload returns the value of this argument; otherwise, failure results in an error message.\nNote that locked ObjectARX applications cannot be unloaded. ObjectARX applications are locked by default.")
           (release-information . nil)
           (history . nil)
           (examples . "Unload the Autoloader application that was loaded in the arxload function example:\n\n(arxunload \"autoloader\")\n\"autoloader\"")
           (url . "https://help.autodesk.com/cloudhelp/2023/ENU/AutoCAD-AutoLISP-Reference/files/GUID-29092087-D1F7-4DF5-863C-FAF4E4F1BC8B.htm")
           (guid . "GUID-29092087-D1F7-4DF5-863C-FAF4E4F1BC8B"))))
    *autolisp-reference-parts*))

(setq *autolisp-reference-parts*
  (cons
    '(("ascii" .
          ((name . "ascii")
           (title . "ascii (AutoLISP)")
           (summary . "Returns the conversion of the first character of a string into its character code (an integer)")
           (source-kind . "AutoLISP")
           (alphabetic-group . "A")
           (feature-groups . ("Conversion"))
           (supported-platforms . "Windows and Mac OS")
           (signature . "(ascii str)")
           (arguments . (("str" . "Type: String\nA single character or text string.")))
           (return-values . "Type: Integer\nA numeric value in the range of 1-65536.")
           (release-information . "Releases:\n- AutoCAD R12 and later on Windows\n- AutoCAD 2011 and later on Mac OS")
           (history . "AutoCAD 2021\n- str\n- argument previously accepted an ASCII text string or character, but now accepts a Unicode text string or character.\n- Return value was modified to support Unicode characters and might be different than earlier releases. For example,\n- (ascii \"€\")\n- previously returned 128, but now returns 8364.\n- LISPSYS system variable controls which AutoLISP engine is used and the behavior of the function.\n-   - 0 - ASCII character support (legacy behavior)\n-   - 1 or 2 - Unicode character support\n- Note: After the value of the LISPSYS system variable has been changed, AutoCAD must be restarted for the change to take affect.")
           (examples . "(ascii \"A\")\n65\n\n(ascii \"a\")\n97\n\n(ascii \"BIG\")\n66\n\n(ascii \"€\")\n8364")
           (url . "https://help.autodesk.com/cloudhelp/2023/ENU/AutoCAD-AutoLISP-Reference/files/GUID-03E1B586-72CB-4AB6-A151-B581AE530318.htm")
           (guid . "GUID-03E1B586-72CB-4AB6-A151-B581AE530318"))))
    *autolisp-reference-parts*))

(setq *autolisp-reference-parts*
  (cons
    '(("assoc" .
          ((name . "assoc")
           (title . "assoc (AutoLISP)")
           (summary . "Searches an association list for an element and returns that association list entry")
           (source-kind . "AutoLISP")
           (alphabetic-group . "A")
           (feature-groups . ("List Manipulation"))
           (supported-platforms . "Windows and Mac OS")
           (signature . "(assoc element alist)")
           (arguments . (("element" . "Type: Integer, Real, or String\nKey of an element in an association list.")
                           ("alist" . "Type: List\nAn association list to be searched.")))
           (return-values . "Type: List or nil\nThe alist entry, if successful. If assoc does not find element as a key in alist, it returns nil.")
           (release-information . nil)
           (history . nil)
           (examples . "(setq al '((name box) (width 3) (size 4.7263) (depth 5)))\n((NAME BOX) (WIDTH 3) (SIZE 4.7263) (DEPTH 5))\n\n(assoc 'size al)\n(SIZE 4.7263)\n\n(assoc 'weight al)\nnil")
           (url . "https://help.autodesk.com/cloudhelp/2023/ENU/AutoCAD-AutoLISP-Reference/files/GUID-46309786-DAF6-4C28-8448-599FBC8A4F6A.htm")
           (guid . "GUID-46309786-DAF6-4C28-8448-599FBC8A4F6A"))))
    *autolisp-reference-parts*))

(setq *autolisp-reference-parts*
  (cons
    '(("atan" .
          ((name . "atan")
           (title . "atan (AutoLISP)")
           (summary . "Returns the arctangent of a number in radians")
           (source-kind . "AutoLISP")
           (alphabetic-group . "A")
           (feature-groups . ("Arithmetic"))
           (supported-platforms . "Windows and Mac OS")
           (signature . "(atan num1 [num2])")
           (arguments . (("num1" . "Type: Integer or Real\nA numeric value.")
                           ("num2" . "Type: Integer or Real\nA numeric value.")))
           (return-values . "Type: Real\nThe arctangent of num1, in radians, if only num1 is supplied. If you supply both num1 and num2 arguments, atan returns the arctangent of num1/num2, in radians. If num2 is zero, it returns an angle of plus or minus 1.570796 radians (+90 degrees or -90 degrees), depending on the sign ofnum1. The range of angles returned is -pi/2 to +pi/2 radians.")
           (release-information . nil)
           (history . nil)
           (examples . "(atan 1)\n0.785398\n\n(atan 1.0)\n0.785398\n\n(atan 0.5)\n0.463648\n\n(atan -1.0)\n-0.785398\n\n(atan 2.0 3.0)\n0.588003\n\n(atan 2.0 -3.0)\n2.55359\n\n(atan 1.0 0.0)\n1.5708")
           (url . "https://help.autodesk.com/cloudhelp/2023/ENU/AutoCAD-AutoLISP-Reference/files/GUID-1A40A16E-8ABE-437D-9888-2F43CEA0B5CE.htm")
           (guid . "GUID-1A40A16E-8ABE-437D-9888-2F43CEA0B5CE"))))
    *autolisp-reference-parts*))

(setq *autolisp-reference-parts*
  (cons
    '(("atof" .
          ((name . "atof")
           (title . "atof (AutoLISP)")
           (summary . "Converts a string into a real number")
           (source-kind . "AutoLISP")
           (alphabetic-group . "A")
           (feature-groups . ("Conversion"))
           (supported-platforms . "Windows and Mac OS")
           (signature . "(atof str)")
           (arguments . (("str" . "Type: String\nA string to be converted into a real number.")))
           (return-values . "Type: Real\nA numeric value.")
           (release-information . nil)
           (history . nil)
           (examples . "(atof \"97.1\")\n97.1\n\n(atof \"3\")\n3.0\n\n(atof \"3.9\")\n3.9")
           (url . "https://help.autodesk.com/cloudhelp/2023/ENU/AutoCAD-AutoLISP-Reference/files/GUID-8618A388-E4CF-40E1-813B-057367DD1840.htm")
           (guid . "GUID-8618A388-E4CF-40E1-813B-057367DD1840"))))
    *autolisp-reference-parts*))

(setq *autolisp-reference-parts*
  (cons
    '(("atoi" .
          ((name . "atoi")
           (title . "atoi (AutoLISP)")
           (summary . "Converts a string into an integer")
           (source-kind . "AutoLISP")
           (alphabetic-group . "A")
           (feature-groups . ("Conversion"))
           (supported-platforms . "Windows and Mac OS")
           (signature . "(atoi str)")
           (arguments . (("str" . "Type: String\nA string to be converted into an integer.")))
           (return-values . "Type: Integer\nA numeric value.")
           (release-information . nil)
           (history . nil)
           (examples . "(atoi \"97\")\n97\n\n(atoi \"3\")\n3\n\n(atoi \"3.9\")\n3")
           (url . "https://help.autodesk.com/cloudhelp/2023/ENU/AutoCAD-AutoLISP-Reference/files/GUID-20EF237C-7079-4E29-860C-B8531D6C7F36.htm")
           (guid . "GUID-20EF237C-7079-4E29-860C-B8531D6C7F36"))))
    *autolisp-reference-parts*))

(setq *autolisp-reference-parts*
  (cons
    '(("atom" .
          ((name . "atom")
           (title . "atom (AutoLISP)")
           (summary . "Verifies that an item is an atom")
           (source-kind . "AutoLISP")
           (alphabetic-group . "A")
           (feature-groups . ("Symbol-Handling"))
           (supported-platforms . "Windows and Mac OS")
           (signature . "(atom item)")
           (arguments . (("item" . "Type: Symbol\nAny AutoLISP element.\nSome versions of LISP differ in their interpretation of atom, so be careful when converting from non-AutoLISP code.")))
           (return-values . "Type: T or nil\nnil if item is a list; otherwise T. Anything that is not a list is considered an atom.")
           (release-information . nil)
           (history . nil)
           (examples . "(setq a '(x y z))\n(X Y Z)\n\n(setq b 'a)\nA\n\n(atom 'a)\nT\n\n(atom a)\nnil\n\n(atom 'b)\nT\n\n(atom b)\nT\n\n(atom '(a b c))\nnil")
           (url . "https://help.autodesk.com/cloudhelp/2023/ENU/AutoCAD-AutoLISP-Reference/files/GUID-3B74E28D-7C3B-4409-9DFE-0305E9881560.htm")
           (guid . "GUID-3B74E28D-7C3B-4409-9DFE-0305E9881560"))))
    *autolisp-reference-parts*))

(setq *autolisp-reference-parts*
  (cons
    '(("atoms-family" .
          ((name . "atoms-family")
           (title . "atoms-family (AutoLISP)")
           (summary . "Returns a list of the currently defined symbols")
           (source-kind . "AutoLISP")
           (alphabetic-group . "A")
           (feature-groups . ("Symbol-Handling"))
           (supported-platforms . "Windows and Mac OS")
           (signature . "(atoms-family format [symlist])")
           (arguments . (("format" . "Type: Integer\nAn integer value of 0 or 1 that determines the format in which atoms-family returns the symbol names:\n0 -- Return the symbol names as a list\n1 -- Return the symbol names as a list of strings")
                           ("symlist" . "Type: List\nA list of strings that specify the symbol names you want atoms-family to search for.")))
           (return-values . "Type: List\nA list of symbols. If you specify symlist, then atoms-family returns the specified symbols that are currently defined, and returns nil for those symbols that are not defined.")
           (release-information . nil)
           (history . nil)
           (examples . "(atoms-family 0)\n(BNS_PRE_SEL FITSTR2LEN C:AI_SPHERE ALERT DEFUN C:BEXTEND REM_GROUP\n B_RESTORE_SYSVARS BNS_CMD_EXIT LISPED FNSPLITL...)\n\nThe following code verifies that the symbols CAR, CDR, and XYZ are defined, and returns the list as strings:\n\n(atoms-family 1 '(\"CAR\" \"CDR\" \"XYZ\"))\n(\"CAR\" \"CDR\" nil)\n\nThe return value shows that the symbol XYZ is not defined.")
           (url . "https://help.autodesk.com/cloudhelp/2023/ENU/AutoCAD-AutoLISP-Reference/files/GUID-0B35850D-9E62-446B-BAA2-0598A4BDE3D7.htm")
           (guid . "GUID-0B35850D-9E62-446B-BAA2-0598A4BDE3D7"))))
    *autolisp-reference-parts*))

(setq *autolisp-reference-parts*
  (cons
    '(("autoarxload" .
          ((name . "autoarxload")
           (title . "autoarxload (AutoLISP)")
           (summary . "Predefines command names to load an associated ObjectARX file")
           (source-kind . "AutoLISP")
           (alphabetic-group . "A")
           (feature-groups . ("Application-Handling"))
           (supported-platforms . "Windows and Mac OS")
           (signature . "(autoarxload filename cmdlist)")
           (arguments . (("filename" . "Type: String\nObjectARX file to be loaded when one of the commands defined by the cmdlist argument is entered at the Command prompt. You can omit the path from the filename, AutoCAD looks for the file in the support file search path. The extension from the filename can also be omitted; .arx (Windows) or .bundle (Mac OS).")
                           ("cmdlist" . "Type: List\nA list of strings.")))
           (return-values . "Type: nil\nAlways returns nil.")
           (release-information . nil)
           (history . nil)
           (examples . "The following code defines the C:APP1, C:APP2, and C:APP3 functions to load the bonusapp.arx or bonusapp.bundle file:\n\n(autoarxload \"BONUSAPP\" '(\"APP1\" \"APP2\" \"APP3\"))")
           (url . "https://help.autodesk.com/cloudhelp/2023/ENU/AutoCAD-AutoLISP-Reference/files/GUID-E1DDBABF-6F72-4747-B9E2-ACEEEA9FAA48.htm")
           (guid . "GUID-E1DDBABF-6F72-4747-B9E2-ACEEEA9FAA48"))))
    *autolisp-reference-parts*))

(setq *autolisp-reference-parts*
  (cons
    '(("autoload" .
          ((name . "autoload")
           (title . "autoload (AutoLISP)")
           (summary . "Predefines command names to load an associated AutoLISP file")
           (source-kind . "AutoLISP")
           (alphabetic-group . "A")
           (feature-groups . ("Application-Handling"))
           (supported-platforms . "Windows and Mac OS")
           (signature . "(autoload filename cmdlist)")
           (arguments . (("filename" . "Type: String\nAutoLISP file to be loaded when one of the commands defined by the cmdlist argument is entered at the Command prompt. You can omit the path from the filename, AutoCAD looks for the file in the support file search path. The extension from the filename can also be omitted; .lsp or .fas, or .vlx (Windows only).")
                           ("cmdlist" . "Type: List\nA list of strings.")))
           (return-values . "Type: nil\nAlways returns nil.\nIf you associate a command with filename and that command is not defined in the specified file, AutoCAD alerts you with an error message when you enter the command.")
           (release-information . nil)
           (history . nil)
           (examples . "The following causes AutoCAD to load the bonusapp.lsp file the first time the APP1, APP2, or APP3 commands are entered at the Command prompt:\n\n(autoload \"BONUSAPP\" '(\"APP1\" \"APP2\" \"APP3\"))")
           (url . "https://help.autodesk.com/cloudhelp/2023/ENU/AutoCAD-AutoLISP-Reference/files/GUID-421B36DE-38EA-4161-9768-01647B5492E8.htm")
           (guid . "GUID-421B36DE-38EA-4161-9768-01647B5492E8"))))
    *autolisp-reference-parts*))

(setq *autolisp-reference-parts*
  (cons
    '(("boole" .
          ((name . "boole")
           (title . "boole (AutoLISP)")
           (summary . "Serves as a general bitwise Boolean function")
           (source-kind . "AutoLISP")
           (alphabetic-group . "B")
           (feature-groups . ("Equality and Conditional"))
           (supported-platforms . "Windows and Mac OS")
           (signature . "(boole operator int1 [int2 ...])")
           (arguments . (("operator" . "Type: Integer\nAn integer between 0 and 15 representing one of the 16 possible Boolean functions in two variables.")
                           ("int1, int2..." . "Type: Integer\nA numeric value.\nNote: boole will accept a single integer argument, but the result is unpredictable.")))
           (return-values . "Type: Integer\nA numeric value.")
           (release-information . nil)
           (history . nil)
           (examples . "The following specifies a logical AND of the values 12 and 5:\n\n(boole 1 12 5)\n3\n\nYou can use other values of operator to perform other Boolean operations for which there are no standard names. For example, if operator is 4, the resulting bits are set if the corresponding bits are set in int2 but not in int1:\n\n(boole 4 3 14)\n12")
           (url . "https://help.autodesk.com/cloudhelp/2023/ENU/AutoCAD-AutoLISP-Reference/files/GUID-C8412B41-BED9-4182-94E6-9EDB3C176D13.htm")
           (guid . "GUID-C8412B41-BED9-4182-94E6-9EDB3C176D13"))))
    *autolisp-reference-parts*))

(setq *autolisp-reference-parts*
  (cons
    '(("boundp" .
          ((name . "boundp")
           (title . "boundp (AutoLISP)")
           (summary . "Verifies if a value is bound to a symbol")
           (source-kind . "AutoLISP")
           (alphabetic-group . "B")
           (feature-groups . ("Symbol-Handling"))
           (supported-platforms . "Windows and Mac OS")
           (signature . "(boundp sym)")
           (arguments . (("sym" . "Type: Symbol\nA symbol.")))
           (return-values . "Type: T or nil\nT if sym has a value bound to it. If no value is bound to sym, or if it has been bound to nil, boundp returns nil. If sym is an undefined symbol, it is automatically created and is bound to nil.")
           (release-information . nil)
           (history . nil)
           (examples . "(setq a 2 b nil)\nnil\n\n(boundp 'a)\nT\n\n(boundp 'b)\nnil\n\nThe atoms-family function provides an alternative method of determining the existence of a symbol without automatically creating the symbol.")
           (url . "https://help.autodesk.com/cloudhelp/2023/ENU/AutoCAD-AutoLISP-Reference/files/GUID-F8491426-8505-4390-825F-CACE15EBB48F.htm")
           (guid . "GUID-F8491426-8505-4390-825F-CACE15EBB48F"))))
    *autolisp-reference-parts*))

(setq *autolisp-reference-parts*
  (cons
    '(("caddr" .
          ((name . "caddr")
           (title . "caddr (AutoLISP)")
           (summary . "Returns the third element of a list")
           (source-kind . "AutoLISP")
           (alphabetic-group . "C")
           (feature-groups . ("List Manipulation"))
           (supported-platforms . "Windows and Mac OS")
           (signature . "(caddr list)")
           (arguments . (("list" . "Type: List\nA list with three or more elements.")))
           (return-values . "Type: Integer, Real, String, List, T or nil\nThe third element in list; otherwise nil, if the list is empty or contains fewer than three elements.")
           (release-information . nil)
           (history . nil)
           (examples . "(setq pt3 '(5.25 1.0 3.0))\n(5.25 1.0 3.0)\n\n(caddr pt3)\n3.0\n\n(caddr '(5.25 1.0))\nnil")
           (url . "https://help.autodesk.com/cloudhelp/2023/ENU/AutoCAD-AutoLISP-Reference/files/GUID-0E81B9F0-7AAD-4BB4-98EB-378AEBE5C4CF.htm")
           (guid . "GUID-0E81B9F0-7AAD-4BB4-98EB-378AEBE5C4CF"))))
    *autolisp-reference-parts*))

(setq *autolisp-reference-parts*
  (cons
    '(("cadr" .
          ((name . "cadr")
           (title . "cadr (AutoLISP)")
           (summary . "Returns the second element of a list")
           (source-kind . "AutoLISP")
           (alphabetic-group . "C")
           (feature-groups . ("List Manipulation"))
           (supported-platforms . "Windows and Mac OS")
           (signature . "(cadr list)")
           (arguments . (("list" . "Type: List\nA list with two or more elements.")))
           (return-values . "Type: Integer, Real, String, List, T or nil\nThe second element in list; otherwise nil, if the list is empty or contains only one element.")
           (release-information . nil)
           (history . nil)
           (examples . "(setq pt2 '(5.25 1.0))\n(5.25 1.0)\n\n(cadr pt2)\n1.0\n\n(cadr '(4.0))\nnil\n\n(cadr '(5.25 1.0 3.0))\n1.0")
           (url . "https://help.autodesk.com/cloudhelp/2023/ENU/AutoCAD-AutoLISP-Reference/files/GUID-F8E9E4F0-218D-4587-9D7E-922BE57C9F9B.htm")
           (guid . "GUID-F8E9E4F0-218D-4587-9D7E-922BE57C9F9B"))))
    *autolisp-reference-parts*))

(setq *autolisp-reference-parts*
  (cons
    '(("car" .
          ((name . "car")
           (title . "car (AutoLISP)")
           (summary . "Returns the first element of a list")
           (source-kind . "AutoLISP")
           (alphabetic-group . "C")
           (feature-groups . ("List Manipulation"))
           (supported-platforms . "Windows and Mac OS")
           (signature . "(car list)")
           (arguments . (("list" . "Type: List\nA list with one or more elements.")))
           (return-values . "Type: Integer, Real, String, List, T or nil\nThe first element in list; otherwise nil, if the list is empty.")
           (release-information . nil)
           (history . nil)
           (examples . "(car '(a b c))\nA\n\n(car '((a b) c))\n(A B)\n\n(car '())\nnil")
           (url . "https://help.autodesk.com/cloudhelp/2023/ENU/AutoCAD-AutoLISP-Reference/files/GUID-2DD1AF33-415C-4C1A-9631-DA958134C53A.htm")
           (guid . "GUID-2DD1AF33-415C-4C1A-9631-DA958134C53A"))))
    *autolisp-reference-parts*))

(setq *autolisp-reference-parts*
  (cons
    '(("cdr" .
          ((name . "cdr")
           (title . "cdr (AutoLISP)")
           (summary . "Returns a list containing all but the first element of the specified list")
           (source-kind . "AutoLISP")
           (alphabetic-group . "C")
           (feature-groups . ("List Manipulation"))
           (supported-platforms . "Windows and Mac OS")
           (signature . "(cdr list)")
           (arguments . (("list" . "Type: List\nA list with two or more elements.")))
           (return-values . "Type: Integer, Real, String, List, T or nil\nA list containing all the elements of list, except the first element. If the list is empty, cdr returns nil.\nNote: When the list argument is a dotted pair, cdr returns the second element without enclosing it in a list.")
           (release-information . nil)
           (history . nil)
           (examples . "(cdr '(a b c))\n(B C)\n\n(cdr '((a b) c))\n(C)\n\n(cdr '())\nnil\n\n(cdr '(a . b))\nB\n\n(cdr '(1 . \"Text\"))\n\"Text\"")
           (url . "https://help.autodesk.com/cloudhelp/2023/ENU/AutoCAD-AutoLISP-Reference/files/GUID-F9CD8FF3-022A-4323-BAE7-390174451537.htm")
           (guid . "GUID-F9CD8FF3-022A-4323-BAE7-390174451537"))))
    *autolisp-reference-parts*))

(setq *autolisp-reference-entry* nil)

(setq *autolisp-reference-value* "GUID-5846BFDD-AE5F-4B2F-99E0-0B9DBA667739")

(setq *autolisp-reference-entry* (cons (cons 'guid *autolisp-reference-value*) *autolisp-reference-entry*))

(setq *autolisp-reference-value* "https://help.autodesk.com/cloudhelp/2023/ENU/AutoCAD-AutoLISP-Reference/files/GUID-5846BFDD-AE5F-4B2F-99E0-0B9DBA667739.htm")

(setq *autolisp-reference-entry* (cons (cons 'url *autolisp-reference-value*) *autolisp-reference-entry*))

(setq *autolisp-reference-value* "(chr 65)\n\"A\"\n\n(chr 66)\n\"B\"\n\n(chr 97)\n\"a\"\n\n(chr 8364)\n\"€\"")

(setq *autolisp-reference-entry* (cons (cons 'examples *autolisp-reference-value*) *autolisp-reference-entry*))

(setq *autolisp-reference-value* "AutoCAD 2021\n- int\n- argument previously accepted an ASCII character code, but now accepts a Unicode character code.\n- Return value changed from an integer in the range of 1-255 (ASCII character codes) to 1-65536 (Unicode character codes) and might be different than earlier releases. For example,\n- (chr 128)\n- previously returned \"€\", but now returns \"\". If you want to return \"€\", your code will need to be updated to\n- (chr 8364)\n- .\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: String\nA single character based on the numeric value of int.")

(setq *autolisp-reference-entry* (cons (cons 'return-values *autolisp-reference-value*) *autolisp-reference-entry*))

(setq *autolisp-reference-value* nil)

(setq *autolisp-reference-string* "Type: Integer\nA numeric value in the range of 1-65536.")

(setq *autolisp-reference-value* (cons (cons "int" *autolisp-reference-string*) *autolisp-reference-value*))

(setq *autolisp-reference-entry* (cons (cons 'arguments *autolisp-reference-value*) *autolisp-reference-entry*))

(setq *autolisp-reference-value* "(chr int)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Conversion"))

(setq *autolisp-reference-entry* (cons (cons 'feature-groups *autolisp-reference-value*) *autolisp-reference-entry*))

(setq *autolisp-reference-value* "C")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Converts an integer representing a character code into a single-character string")

(setq *autolisp-reference-entry* (cons (cons 'summary *autolisp-reference-value*) *autolisp-reference-entry*))

(setq *autolisp-reference-value* "chr (AutoLISP)")

(setq *autolisp-reference-entry* (cons (cons 'title *autolisp-reference-value*) *autolisp-reference-entry*))

(setq *autolisp-reference-value* "chr")

(setq *autolisp-reference-entry* (cons (cons 'name *autolisp-reference-value*) *autolisp-reference-entry*))

(setq *autolisp-reference-parts* (cons (list (cons "chr" *autolisp-reference-entry*)) *autolisp-reference-parts*))

(setq *autolisp-reference-parts*
  (cons
    '(("client_data_tile" .
          ((name . "client_data_tile")
           (title . "client_data_tile (AutoLISP/DCL)")
           (summary . "Associates application-managed data with a dialog box tile")
           (source-kind . "AutoLISP/DCL")
           (alphabetic-group . "C")
           (feature-groups . ("Application-Specific Data-Handling Function Reference (AutoLISP/DCL)"))
           (supported-platforms . "Windows and Mac OS")
           (signature . "(client_data_tile key clientdata)")
           (arguments . (("key" . "Type: String\nValue that specifies a tile. This argument is case-sensitive.")
                           ("clientdata" . "Type: String\nValue to be associated with the key tile. An action expression or callback function can refer to the string as $data.")))
           (return-values . "Always returns nil.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-9790A095-68BA-40FB-B89E-036F276CCF56.htm")
           (guid . "GUID-9790A095-68BA-40FB-B89E-036F276CCF56"))))
    *autolisp-reference-parts*))

(setq *autolisp-reference-parts*
  (cons
    '(("close" .
          ((name . "close")
           (title . "close (AutoLISP)")
           (summary . "Closes an open file")
           (source-kind . "AutoLISP")
           (alphabetic-group . "C")
           (feature-groups . ("File-Handling"))
           (supported-platforms . "Windows and Mac OS")
           (signature . "(close file-desc)")
           (arguments . (("file-desc" . "Type: File\nA file descriptor obtained from the open function.")))
           (return-values . "Type: nil\nnil if file-desc is valid; otherwise results in an error message.\nAfter a close, the file descriptor is unchanged but is no longer valid. Data added to an open file is not actually written until the file is closed.")
           (release-information . nil)
           (history . nil)
           (examples . "The following code counts the number of lines in the file somefile.txt and sets the variable ct equal to that number:\n\n(setq fil \"SOMEFILE.TXT\")\n(setq x (open fil \"r\") ct 0)\n(while (read-line x)\n  (setq ct (1+ ct))\n)\n(close x)")
           (url . "https://help.autodesk.com/cloudhelp/2023/ENU/AutoCAD-AutoLISP-Reference/files/GUID-5308ADB6-7C46-43BE-8B6C-B32FBA8982DB.htm")
           (guid . "GUID-5308ADB6-7C46-43BE-8B6C-B32FBA8982DB"))))
    *autolisp-reference-parts*))

(setq *autolisp-reference-parts*
  (cons
    '(("command" .
          ((name . "command")
           (title . "command (AutoLISP)")
           (summary . "Executes an AutoCAD command")
           (source-kind . "AutoLISP")
           (alphabetic-group . "C")
           (feature-groups . ("Query and Command"))
           (supported-platforms . "Windows and Mac OS")
           (signature . "(command [arguments ...])")
           (arguments . (("arguments" . "Type: Integer, Real, String, or List\nAutoCAD commands and their options.\nThe arguments to the command function can be strings, reals, integers, or points, as expected by the prompt sequence of the executed command. A null string (\"\") is equivalent to pressing Enter on the keyboard. Invoking command with no argument is equivalent to pressing Esc and cancels most AutoCAD commands.")))
           (return-values . "Type: nil\nAlways returns nil.")
           (release-information . nil)
           (history . nil)
           (examples . "The following example sets two variables pt1 and pt2 equal to two point values 1,1 and 1,5. It then uses the command function to issue the AutoCAD LINE command and pass the two point values.\n\n(setq pt1 '(1 1) pt2 '(1 5))\n(1 5)\n\n(command \"._line\" pt1 pt2 \"\")\nnil")
           (url . "https://help.autodesk.com/cloudhelp/2023/ENU/AutoCAD-AutoLISP-Reference/files/GUID-1C989B35-2C5A-47EC-A0C9-71998EDFB157.htm")
           (guid . "GUID-1C989B35-2C5A-47EC-A0C9-71998EDFB157"))))
    *autolisp-reference-parts*))

(setq *autolisp-reference-entry* nil)

(setq *autolisp-reference-value* "GUID-5C9DC003-3DD2-4770-95E7-7E19A4EE19A1")

(setq *autolisp-reference-entry* (cons (cons 'guid *autolisp-reference-value*) *autolisp-reference-entry*))

(setq *autolisp-reference-value* "https://help.autodesk.com/cloudhelp/2023/ENU/AutoCAD-AutoLISP-Reference/files/GUID-5C9DC003-3DD2-4770-95E7-7E19A4EE19A1.htm")

(setq *autolisp-reference-entry* (cons (cons 'url *autolisp-reference-value*) *autolisp-reference-entry*))

(setq *autolisp-reference-value* "The following example demonstrates how to execute the AutoCAD CIRCLE command and create a circle with a diameter of 2.75.\n\nCommand: (command-s \"._circle\" \"5,4\" \"_d\" 2.75)\nnil\n\nThe following example demonstrates how to prompt the user for the center point of the circle.\n\nCommand: (setq cPt (getpoint \"\\nSpecify center point: \"))\n(5.0 4.0 0.0)\n\nCommand: (command-s \"._circle\" cPt \"_d\" 2.75)\nnil\n\nThe following is an invalid use of prompting for user input with the command-s function.\n\nCommand: (command-s \"._circle\" (getpoint \"\\nSpecify center point: \") \"_d\" 2.75)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: nil\nnil is returned by the function when the command is done executing on the provided arguments. An *error* is returned when the function fails to complete successfully.")

(setq *autolisp-reference-entry* (cons (cons 'return-values *autolisp-reference-value*) *autolisp-reference-entry*))

(setq *autolisp-reference-value* nil)

(setq *autolisp-reference-string* "Type: Integer, Real, String, or List\nThe command input to supply to the command being executed.\nThe arguments to the command function can be strings, reals, integers, or points, as expected by the prompt sequence of the executed command. A null string (\"\") is equivalent to pressing Enter on the keyboard.")

(setq *autolisp-reference-value* (cons (cons "arguments" *autolisp-reference-string*) *autolisp-reference-value*))

(setq *autolisp-reference-string* "Type: String\nName of the command to execute.")

(setq *autolisp-reference-value* (cons (cons "cmdname" *autolisp-reference-string*) *autolisp-reference-value*))

(setq *autolisp-reference-entry* (cons (cons 'arguments *autolisp-reference-value*) *autolisp-reference-entry*))

(setq *autolisp-reference-value* "(command-s [cmdname [arguments ...]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Query and Command"))

(setq *autolisp-reference-entry* (cons (cons 'feature-groups *autolisp-reference-value*) *autolisp-reference-entry*))

(setq *autolisp-reference-value* "C")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Executes an AutoCAD command and the supplied input")

(setq *autolisp-reference-entry* (cons (cons 'summary *autolisp-reference-value*) *autolisp-reference-entry*))

(setq *autolisp-reference-value* "command-s (AutoLISP)")

(setq *autolisp-reference-entry* (cons (cons 'title *autolisp-reference-value*) *autolisp-reference-entry*))

(setq *autolisp-reference-value* "command-s")

(setq *autolisp-reference-entry* (cons (cons 'name *autolisp-reference-value*) *autolisp-reference-entry*))

(setq *autolisp-reference-parts* (cons (list (cons "command-s" *autolisp-reference-entry*)) *autolisp-reference-parts*))

(setq *autolisp-reference-entry* nil)

(setq *autolisp-reference-value* "GUID-7BA45202-D95F-4F2D-8D83-965024826074")

(setq *autolisp-reference-entry* (cons (cons 'guid *autolisp-reference-value*) *autolisp-reference-entry*))

(setq *autolisp-reference-value* "https://help.autodesk.com/cloudhelp/2023/ENU/AutoCAD-AutoLISP-Reference/files/GUID-7BA45202-D95F-4F2D-8D83-965024826074.htm")

(setq *autolisp-reference-entry* (cons (cons 'url *autolisp-reference-value*) *autolisp-reference-entry*))

(setq *autolisp-reference-value* "The following example uses cond to perform an absolute value calculation:\n\n(cond\n   ((minusp a) (- a))\n   (t a)\n)\n\nIf the variable a is set to the value-10, this returns 10.\n\nAs shown, cond can be used as a case type function. It is common to use T as the last (default) test expression. Here's another simple example. Given a user response string in the variable s, this function tests the response and returns 1 if it is Y or y, 0 if it is N or n; otherwise nil.\n\n(cond\n   ((= s \"Y\") 1)\n   ((= s \"y\") 1)\n   ((= s \"N\") 0)\n   ((= s \"n\") 0)\n   (t nil)\n)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nThe value of the last expression in the sublist. If there is only one expression in the sublist (that is, if result is missing), the value of the test expression is returned. If no arguments are supplied, cond returns nil.")

(setq *autolisp-reference-entry* (cons (cons 'return-values *autolisp-reference-value*) *autolisp-reference-entry*))

(setq *autolisp-reference-value* nil)

(setq *autolisp-reference-string* "Type: List\nArguments that are executed if the test condition is successful.")

(setq *autolisp-reference-value* (cons (cons "result" *autolisp-reference-string*) *autolisp-reference-value*))

(setq *autolisp-reference-string* "Type: List\nTest condition to be evaluated.")

(setq *autolisp-reference-value* (cons (cons "test" *autolisp-reference-string*) *autolisp-reference-value*))

(setq *autolisp-reference-entry* (cons (cons 'arguments *autolisp-reference-value*) *autolisp-reference-entry*))

(setq *autolisp-reference-value* "(cond [((test) (result ...)) ...])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Equality and Conditional"))

(setq *autolisp-reference-entry* (cons (cons 'feature-groups *autolisp-reference-value*) *autolisp-reference-entry*))

(setq *autolisp-reference-value* "C")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Serves as the primary conditional function for AutoLISP")

(setq *autolisp-reference-entry* (cons (cons 'summary *autolisp-reference-value*) *autolisp-reference-entry*))

(setq *autolisp-reference-value* "cond (AutoLISP)")

(setq *autolisp-reference-entry* (cons (cons 'title *autolisp-reference-value*) *autolisp-reference-entry*))

(setq *autolisp-reference-value* "cond")

(setq *autolisp-reference-entry* (cons (cons 'name *autolisp-reference-value*) *autolisp-reference-entry*))

(setq *autolisp-reference-parts* (cons (list (cons "cond" *autolisp-reference-entry*)) *autolisp-reference-parts*))

(setq *autolisp-reference-parts*
  (cons
    '(("cons" .
          ((name . "cons")
           (title . "cons (AutoLISP)")
           (summary . "Adds an element to the beginning of a list, or constructs a dotted list")
           (source-kind . "AutoLISP")
           (alphabetic-group . "C")
           (feature-groups . ("List Manipulation"))
           (supported-platforms . "Windows and Mac OS")
           (signature . "(cons new-first-element list-or-atom)")
           (arguments . (("new-first-element" . "Type: Integer, Real, String, List, T, or nil\nElement to be added to the beginning of a list. This element can be an atom or a list.")
                           ("list-or-atom" . "Type: Integer, Real, String, List, or T\nA list or an atom.")))
           (return-values . "Type: List\nThe value returned depends on the data type of list-or-atom. If list-or-atom is a list, cons returns that list with new-first-element added as the first item in the list. If list-or-atom is an atom, cons returns a dotted pair consisting of new-first-element and list-or-atom.")
           (release-information . nil)
           (history . nil)
           (examples . "(cons 'a '(b c d))\n(A B C D)\n\n(cons '(a) '(b c d))\n((A) B C D)\n\n(cons 'a 2)\n(A . 2)")
           (url . "https://help.autodesk.com/cloudhelp/2023/ENU/AutoCAD-AutoLISP-Reference/files/GUID-33B418E7-DB3D-4CBE-954E-F070F0A7CB2B.htm")
           (guid . "GUID-33B418E7-DB3D-4CBE-954E-F070F0A7CB2B"))))
    *autolisp-reference-parts*))

(setq *autolisp-reference-parts*
  (cons
    '(("cos" .
          ((name . "cos")
           (title . "cos (AutoLISP)")
           (summary . "Returns the cosine of an angle expressed in radians")
           (source-kind . "AutoLISP")
           (alphabetic-group . "C")
           (feature-groups . ("Arithmetic"))
           (supported-platforms . "Windows and Mac OS")
           (signature . "(cos ang)")
           (arguments . (("ang" . "Type: Integer or Real\nAn angle, in radians.")))
           (return-values . "Type: Real\nThe cosine of ang, in radians.")
           (release-information . nil)
           (history . nil)
           (examples . "(cos 0.0)\n1.0\n\n(cos pi)\n-1.0")
           (url . "https://help.autodesk.com/cloudhelp/2023/ENU/AutoCAD-AutoLISP-Reference/files/GUID-5F39D690-A986-498D-929A-56BC891E08CD.htm")
           (guid . "GUID-5F39D690-A986-498D-929A-56BC891E08CD"))))
    *autolisp-reference-parts*))

(setq *autolisp-reference-parts*
  (cons
    '(("cvunit" .
          ((name . "cvunit")
           (title . "cvunit (AutoLISP)")
           (summary . "Converts a value from one unit of measurement to another")
           (source-kind . "AutoLISP")
           (alphabetic-group . "C")
           (feature-groups . ("Conversion"))
           (supported-platforms . "Windows and Mac OS")
           (signature . "(cvunit value from-unit to-unit)")
           (arguments . (("value" . "Type: Integer, Real, or List\nThe numeric value or point list (2D or 3D point) to be converted.")
                           ("from-unit" . "Type: String\nThe unit that value is being converted from.")
                           ("to-unit" . "Type: String\nThe unit that value is being converted to.")))
           (return-values . "Type: Real, List, or nil\nThe converted value, if successful; otherwise nil, if either unit name is unknown (not found in the acad.unt file), or if the two units are incompatible (for example, trying to convert grams into years).")
           (release-information . nil)
           (history . nil)
           (examples . "(cvunit 1 \"minute\" \"second\")\n60.0\n\n(cvunit 1 \"gallon\" \"furlong\")\nnil\n\n(cvunit 1.0 \"inch\" \"cm\")\n2.54\n\n(cvunit 1.0 \"acre\" \"sq yard\")\n4840.0\n\n(cvunit '(1.0 2.5) \"ft\" \"in\")\n(12.0 30.0)\n\n(cvunit '(1 2 3) \"ft\" \"in\")\n(12.0 24.0 36.0)")
           (url . "https://help.autodesk.com/cloudhelp/2023/ENU/AutoCAD-AutoLISP-Reference/files/GUID-253E72F1-09B8-473E-A51B-B97BE2E29019.htm")
           (guid . "GUID-253E72F1-09B8-473E-A51B-B97BE2E29019"))))
    *autolisp-reference-parts*))

(setq *autolisp-reference-entry* nil)

(setq *autolisp-reference-value* "GUID-5269529D-A013-4AB4-AAB7-DBA1C7CA73EB")

(setq *autolisp-reference-entry* (cons (cons 'guid *autolisp-reference-value*) *autolisp-reference-entry*))

(setq *autolisp-reference-value* "https://help.autodesk.com/cloudhelp/2023/ENU/AutoCAD-AutoLISP-Reference/files/GUID-5269529D-A013-4AB4-AAB7-DBA1C7CA73EB.htm")

(setq *autolisp-reference-entry* (cons (cons 'url *autolisp-reference-value*) *autolisp-reference-entry*))

(setq *autolisp-reference-value* "(defun myfunc (x y) ...)         Function takes two arguments\n(defun myfunc (/ a b) ...)       Function has two local variables\n(defun myfunc (x / temp) ...)    One argument, one local variable\n(defun myfunc () ...)            No arguments or local variables")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "The result of the last expression evaluated.\nCaution: Never use the name of a built-in function or symbol for the sym argument to defun. This overwrites the original definition and makes the built-in function or symbol inaccessible. To get a list of built-in and previously defined functions, use the atoms-family function.")

(setq *autolisp-reference-entry* (cons (cons 'return-values *autolisp-reference-value*) *autolisp-reference-entry*))

(setq *autolisp-reference-value* nil)

(setq *autolisp-reference-string* "Type: List\nAny number of AutoLISP expressions to be evaluated when the function executes.")

(setq *autolisp-reference-value* (cons (cons "expr" *autolisp-reference-string*) *autolisp-reference-value*))

(setq *autolisp-reference-string* "Type: Symbol\nThe names of one or more local variables for the function.\nThe slash preceding the variable names must be separated from the first local name and from the last argument, if any, by at least one space.")

(setq *autolisp-reference-value* (cons (cons "/ variables" *autolisp-reference-string*) *autolisp-reference-value*))

(setq *autolisp-reference-string* "Type: Integer, Real, String, List, T, or nil\nThe names of arguments expected by the function.")

(setq *autolisp-reference-value* (cons (cons "arguments" *autolisp-reference-string*) *autolisp-reference-value*))

(setq *autolisp-reference-string* "Type: Symbol\nA symbol naming the function.")

(setq *autolisp-reference-value* (cons (cons "sym" *autolisp-reference-string*) *autolisp-reference-value*))

(setq *autolisp-reference-entry* (cons (cons 'arguments *autolisp-reference-value*) *autolisp-reference-entry*))

(setq *autolisp-reference-value* "(defun sym ([arguments] [/ variables ...]) expr ...)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Function-Handling"))

(setq *autolisp-reference-entry* (cons (cons 'feature-groups *autolisp-reference-value*) *autolisp-reference-entry*))

(setq *autolisp-reference-value* "D")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Defines a function")

(setq *autolisp-reference-entry* (cons (cons 'summary *autolisp-reference-value*) *autolisp-reference-entry*))

(setq *autolisp-reference-value* "defun (AutoLISP)")

(setq *autolisp-reference-entry* (cons (cons 'title *autolisp-reference-value*) *autolisp-reference-entry*))

(setq *autolisp-reference-value* "defun")

(setq *autolisp-reference-entry* (cons (cons 'name *autolisp-reference-value*) *autolisp-reference-entry*))

(setq *autolisp-reference-parts* (cons (list (cons "defun" *autolisp-reference-entry*)) *autolisp-reference-parts*))

(setq *autolisp-reference-parts*
  (cons
    '(("defun-q" .
          ((name . "defun-q")
           (title . "defun-q (AutoLISP)")
           (summary . "Defines a function as a list")
           (source-kind . "AutoLISP")
           (alphabetic-group . "D")
           (feature-groups . ("Function-Handling"))
           (supported-platforms . "Windows and Mac OS")
           (signature . "(defun-q sym ([arguments] [/ variables ...]) expr ...)")
           (arguments . (("sym" . "Type: Symbol\nA symbol naming the function.")
                           ("arguments" . "Type: Integer, Real, String, List, T, or nil\nThe names of arguments expected by the function.")
                           ("/ variables" . "Type: Symbol\nThe names of one or more local variables for the function.\nThe slash preceding the variable names must be separated from the first local name and from the last argument, if any, by at least one space.")
                           ("expr" . "Type: List\nAny number of AutoLISP expressions to be evaluated when the function executes.")))
           (return-values . "Type: List or Symbol\nThe result of the last expression evaluated.")
           (release-information . nil)
           (history . nil)
           (examples . "(defun-q my-startup (x) (print (list x)))\nMY-STARTUP\n\n(my-startup 5)\n(5) (5)\n\nUse defun-q-list-ref to display the list structure of my-startup:\n\n(defun-q-list-ref 'my-startup)\n((X) (PRINT (LIST X)))")
           (url . "https://help.autodesk.com/cloudhelp/2023/ENU/AutoCAD-AutoLISP-Reference/files/GUID-5EE138EF-D531-441B-9F12-8D5645C540FE.htm")
           (guid . "GUID-5EE138EF-D531-441B-9F12-8D5645C540FE"))))
    *autolisp-reference-parts*))

(setq *autolisp-reference-parts*
  (cons
    '(("defun-q-list-ref" .
          ((name . "defun-q-list-ref")
           (title . "defun-q-list-ref (AutoLISP)")
           (summary . "Displays the list structure of a function defined with defun-q")
           (source-kind . "AutoLISP")
           (alphabetic-group . "D")
           (feature-groups . ("Function-Handling"))
           (supported-platforms . "Windows and Mac OS")
           (signature . "(defun-q-list-ref 'function )")
           (arguments . (("function" . "Type: Symbol\nA symbol naming the function.")))
           (return-values . "Type: List, Symbol, or nil\nThe list definition of the function; otherwise nil, if the argument is not a list.")
           (release-information . nil)
           (history . nil)
           (examples . "Define a function using defun-q:\n\n(defun-q my-startup (x) (print (list x)))\nMY-STARTUP\n\nUse defun-q-list-ref to display the list structure of my-startup:\n\n(defun-q-list-ref 'my-startup)\n((X) (PRINT (LIST X)))")
           (url . "https://help.autodesk.com/cloudhelp/2023/ENU/AutoCAD-AutoLISP-Reference/files/GUID-DAF4A76E-9346-4A68-A0C8-17695177033B.htm")
           (guid . "GUID-DAF4A76E-9346-4A68-A0C8-17695177033B"))))
    *autolisp-reference-parts*))

(setq *autolisp-reference-entry* nil)

(setq *autolisp-reference-value* "GUID-CDA30337-9889-4D33-9461-503F307D1360")

(setq *autolisp-reference-entry* (cons (cons 'guid *autolisp-reference-value*) *autolisp-reference-entry*))

(setq *autolisp-reference-value* "https://help.autodesk.com/cloudhelp/2023/ENU/AutoCAD-AutoLISP-Reference/files/GUID-CDA30337-9889-4D33-9461-503F307D1360.htm")

(setq *autolisp-reference-entry* (cons (cons 'url *autolisp-reference-value*) *autolisp-reference-entry*))

(setq *autolisp-reference-value* "(defun-q-list-set 'foo '((x) x))\nFOO\n\n(foo 3)\n3\n\nThe following example illustrates the use of defun-q-list-set to combine two functions into a single function with defun-q:\n\n(defun-q s::startup (x) (print x))\nS::STARTUP\n\n(defun-q my-startup (x) (print (list x)))\nMY-STARTUP\n\nUse defun-q-list-set to combine the functions into a single function:\n\n(defun-q-list-set 's::startup (append\n   (defun-q-list-ref 's::startup)\n   (cdr (defun-q-list-ref 'my-startup))))\nS::STARTUP\n\nThe following illustrates how the functions respond individually, and how the functions work after being combined using defun-q-list-set:\n\n(defun-q foo (x) (print (list 'foo x)))\nFOO\n\n(foo 1)\n(FOO 1) (FOO 1)\n\n(defun-q bar (x) (print (list 'bar x)))\nBAR\n\n(bar 2)\n(BAR 2) (BAR 2)\n\n(defun-q-list-set\n  'foo\n  (append (defun-q-list-ref 'foo)\n              (cdr (defun-q-list-ref 'bar))\n  ))\nF")

(setq *autolisp-reference-value* (strcat *autolisp-reference-value* "OO\n\n(foo 3)\n(FOO 3)\n(BAR 3) (BAR 3)"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List, Symbol, or nil\nThe sym defined.")

(setq *autolisp-reference-entry* (cons (cons 'return-values *autolisp-reference-value*) *autolisp-reference-entry*))

(setq *autolisp-reference-value* nil)

(setq *autolisp-reference-string* "Type: List\nA list containing the expressions to be included in the function.")

(setq *autolisp-reference-value* (cons (cons "list" *autolisp-reference-string*) *autolisp-reference-value*))

(setq *autolisp-reference-string* "Type: Symbol\nA symbol naming the function")

(setq *autolisp-reference-value* (cons (cons "sym" *autolisp-reference-string*) *autolisp-reference-value*))

(setq *autolisp-reference-entry* (cons (cons 'arguments *autolisp-reference-value*) *autolisp-reference-entry*))

(setq *autolisp-reference-value* "(defun-q-list-set 'sym list)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Function-Handling"))

(setq *autolisp-reference-entry* (cons (cons 'feature-groups *autolisp-reference-value*) *autolisp-reference-entry*))

(setq *autolisp-reference-value* "D")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Sets the value of a symbol to be a function defined by a list")

(setq *autolisp-reference-entry* (cons (cons 'summary *autolisp-reference-value*) *autolisp-reference-entry*))

(setq *autolisp-reference-value* "defun-q-list-set (AutoLISP)")

(setq *autolisp-reference-entry* (cons (cons 'title *autolisp-reference-value*) *autolisp-reference-entry*))

(setq *autolisp-reference-value* "defun-q-list-set")

(setq *autolisp-reference-entry* (cons (cons 'name *autolisp-reference-value*) *autolisp-reference-entry*))

(setq *autolisp-reference-parts* (cons (list (cons "defun-q-list-set" *autolisp-reference-entry*)) *autolisp-reference-parts*))

(setq *autolisp-reference-entry* nil)

(setq *autolisp-reference-value* "GUID-5931D6D8-7F6E-4773-B08C-DEC5F9C4A22E")

(setq *autolisp-reference-entry* (cons (cons 'guid *autolisp-reference-value*) *autolisp-reference-entry*))

(setq *autolisp-reference-value* "https://help.autodesk.com/cloudhelp/2023/ENU/AutoCAD-AutoLISP-Reference/files/GUID-5931D6D8-7F6E-4773-B08C-DEC5F9C4A22E.htm")

(setq *autolisp-reference-entry* (cons (cons 'url *autolisp-reference-value*) *autolisp-reference-entry*))

(setq *autolisp-reference-value* "The examples that follow create objects and add them to the named object dictionary.\n\nCreate a dictionary entry list:\n\n(setq dictionary (list '(0 . \"DICTIONARY\") '(100 . \"AcDbDictionary\")))\n((0 . \"DICTIONARY\") (100 . \"AcDbDictionary\"))\n\nCreate a dictionary object using the entmakex function:\n\n(setq xname (entmakex dictionary))(setq xname (entmakex dictionary))\n<Entity name: 1d98950>\n\nAdd the dictionary to the named object dictionary:\n\n(setq newdict (dictadd (namedobjdict) \"MY_WAY_COOL_DICTIONARY\" xname))\n<Entity name: 1d98950>\n\nCreate an Xrecord list:\n\n(setq datalist (append (list '(0 . \"XRECORD\")\n                                 '(100 . \"AcDbXrecord\"))\n                                 '((1 . \"This is my data\") (10 1. 2. 3.) (70 . 33))))\n((0 . \"XRECORD\") (100 . \"AcDbXrecord\") (1 . \"This is my data\") (10 1.0 2.0 3.0) (70 . 33))\n\nMake an Xrecor")

(setq *autolisp-reference-value* (strcat *autolisp-reference-value* "d object:\n\n(setq xname (entmakex datalist))\n<Entity name: 1d98958>\n\nAdd the Xrecord object to the dictionary:\n\n(dictadd newdict \"DATA_RECORD_1\" xname)\n<Entity name: 1d98958>"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Ename (entity name)\nThe entity name of the object added to the dictionary.")

(setq *autolisp-reference-entry* (cons (cons 'return-values *autolisp-reference-value*) *autolisp-reference-entry*))

(setq *autolisp-reference-value* nil)

(setq *autolisp-reference-string* "Type: Ename (entity name)\nA nongraphical object to be added to the dictionary.")

(setq *autolisp-reference-value* (cons (cons "newobj" *autolisp-reference-string*) *autolisp-reference-value*))

(setq *autolisp-reference-string* "Type: String\nThe key name of the object being added to the dictionary; symbol must be a unique name that does not already exist in the dictionary.")

(setq *autolisp-reference-value* (cons (cons "symbol" *autolisp-reference-string*) *autolisp-reference-value*))

(setq *autolisp-reference-string* "Type: Ename (entity name)\nName of the dictionary the object is being added to.")

(setq *autolisp-reference-value* (cons (cons "ename" *autolisp-reference-string*) *autolisp-reference-value*))

(setq *autolisp-reference-entry* (cons (cons 'arguments *autolisp-reference-value*) *autolisp-reference-entry*))

(setq *autolisp-reference-value* "(dictadd ename symbol newobj)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Symbol Table and Dictionary-Handling"))

(setq *autolisp-reference-entry* (cons (cons 'feature-groups *autolisp-reference-value*) *autolisp-reference-entry*))

(setq *autolisp-reference-value* "D")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Adds a nongraphical object to the specified dictionary")

(setq *autolisp-reference-entry* (cons (cons 'summary *autolisp-reference-value*) *autolisp-reference-entry*))

(setq *autolisp-reference-value* "dictadd (AutoLISP)")

(setq *autolisp-reference-entry* (cons (cons 'title *autolisp-reference-value*) *autolisp-reference-entry*))

(setq *autolisp-reference-value* "dictadd")

(setq *autolisp-reference-entry* (cons (cons 'name *autolisp-reference-value*) *autolisp-reference-entry*))

(setq *autolisp-reference-parts* (cons (list (cons "dictadd" *autolisp-reference-entry*)) *autolisp-reference-parts*))

(setq *autolisp-reference-entry* nil)

(setq *autolisp-reference-value* "GUID-8596E2E9-FEB5-4995-ADE4-31287864C0CB")

(setq *autolisp-reference-entry* (cons (cons 'guid *autolisp-reference-value*) *autolisp-reference-entry*))

(setq *autolisp-reference-value* "https://help.autodesk.com/cloudhelp/2023/ENU/AutoCAD-AutoLISP-Reference/files/GUID-8596E2E9-FEB5-4995-ADE4-31287864C0CB.htm")

(setq *autolisp-reference-entry* (cons (cons 'url *autolisp-reference-value*) *autolisp-reference-entry*))

(setq *autolisp-reference-value* "Create a dictionary and an entry as shown in the example for dictadd. Then make another Xrecord object:\n\n(setq xname (entmakex datalist))\n<Entity name: 1b62d60>\n\nAdd this Xrecord object to the dictionary, as the second record in the dictionary:\n\n(dictadd newdict \"DATA_RECORD_2\" xname)\n<Entity name: 1b62d60>\n\nReturn the entity name of the next entry in the dictionary:\n\n(cdr (car (dictnext newdict)))\n<Entity name: 1bac958>\n\ndictnext returns the name of the first entity added to the dictionary.\n\nReturn the entity name of the next entry in the dictionary:\n\n(cdr (car (dictnext newdict)))\n<Entity name: 1bac960>\n\ndictnext returns the name of the second entity added to the dictionary.\n\nReturn the entity name of the next entry in the dictionary:\n\n(cdr (car (dictnext newdict)))\nnil\n\nThere are no more entries in the dictionary, so dictnext returns nil.\n\nRewind to th")

(setq *autolisp-reference-value* (strcat *autolisp-reference-value* "e first entry in the dictionary and return the entity name of that entry:\n\n(cdr (car (dictnext newdict T)))\n<Entity name: 1bac958>\n\nSpecifying T for the optional rewind argument causes dictnext to return the first entry in the dictionary."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Ename (entity name)\nThe next entry in the specified dictionary; otherwise nil, when the end of the dictionary is reached. Entries are returned as lists of dotted pairs of DXF-type codes and values. Deleted dictionary entries are not returned.\nThe dictsearch function specifies the initial entry retrieved.\nUse namedobjdict to obtain the master dictionary entity name.\nNote: Once you begin stepping through the contents of a dictionary, passing a different dictionary name to dictnext will cause the place to be lost in the original dictionary. In other words, only one global iterator is maintained for use in this function.")

(setq *autolisp-reference-entry* (cons (cons 'return-values *autolisp-reference-value*) *autolisp-reference-entry*))

(setq *autolisp-reference-value* nil)

(setq *autolisp-reference-string* "Type: T or nil\nIf this argument is present and is not nil, the dictionary is rewound and the first entry in it is retrieved.")

(setq *autolisp-reference-value* (cons (cons "rewind" *autolisp-reference-string*) *autolisp-reference-value*))

(setq *autolisp-reference-string* "Type: Ename (entity name)\nName of the dictionary being viewed.")

(setq *autolisp-reference-value* (cons (cons "ename" *autolisp-reference-string*) *autolisp-reference-value*))

(setq *autolisp-reference-entry* (cons (cons 'arguments *autolisp-reference-value*) *autolisp-reference-entry*))

(setq *autolisp-reference-value* "(dictnext ename [rewind])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Symbol Table and Dictionary-Handling"))

(setq *autolisp-reference-entry* (cons (cons 'feature-groups *autolisp-reference-value*) *autolisp-reference-entry*))

(setq *autolisp-reference-value* "D")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Finds the next item in a dictionary")

(setq *autolisp-reference-entry* (cons (cons 'summary *autolisp-reference-value*) *autolisp-reference-entry*))

(setq *autolisp-reference-value* "dictnext (AutoLISP)")

(setq *autolisp-reference-entry* (cons (cons 'title *autolisp-reference-value*) *autolisp-reference-entry*))

(setq *autolisp-reference-value* "dictnext")

(setq *autolisp-reference-entry* (cons (cons 'name *autolisp-reference-value*) *autolisp-reference-entry*))

(setq *autolisp-reference-parts* (cons (list (cons "dictnext" *autolisp-reference-entry*)) *autolisp-reference-parts*))

(setq *autolisp-reference-parts*
  (cons
    '(("dictremove" .
          ((name . "dictremove")
           (title . "dictremove (AutoLISP)")
           (summary . "Removes an entry from the specified dictionary")
           (source-kind . "AutoLISP")
           (alphabetic-group . "D")
           (feature-groups . ("Symbol Table and Dictionary-Handling"))
           (supported-platforms . "Windows and Mac OS")
           (signature . "(dictremove ename symbol)")
           (arguments . (("ename" . "Type: Ename (entity name)\nName of the dictionary being modified.")
                           ("symbol" . "Type: String\nThe entry to be removed from ename.")))
           (return-values . "Type: Ename (entity name) or nil\nThe entity name of the removed entry. If ename is invalid or symbol is not found, dictremove returns nil.")
           (release-information . nil)
           (history . nil)
           (examples . "The following example removes the dictionary created in the dictadd example:\n\n(dictremove (namedobjdict) \"my_way_cool_dictionary\")\n<Entity name: 1d98950>")
           (url . "https://help.autodesk.com/cloudhelp/2023/ENU/AutoCAD-AutoLISP-Reference/files/GUID-0A888F13-7C2A-4CB6-B849-56B72EAC972A.htm")
           (guid . "GUID-0A888F13-7C2A-4CB6-B849-56B72EAC972A"))))
    *autolisp-reference-parts*))

(setq *autolisp-reference-parts*
  (cons
    '(("dictrename" .
          ((name . "dictrename")
           (title . "dictrename (AutoLISP)")
           (summary . "Renames a dictionary entry")
           (source-kind . "AutoLISP")
           (alphabetic-group . "D")
           (feature-groups . ("Symbol Table and Dictionary-Handling"))
           (supported-platforms . "Windows and Mac OS")
           (signature . "(dictrename ename oldsym newsym)")
           (arguments . (("ename" . "Type: Ename (entity name)\nName of the dictionary being modified.")
                           ("oldsym" . "Type: String\nOriginal key name of the entry.")
                           ("newsym" . "Type: String\nNew key name of the entry.")))
           (return-values . "Type: String or nil\nThe newsym value, if the rename is successful. If the oldname is not present in the dictionary, or if ename or newname is invalid, or if newname is already present in the dictionary, then dictrename returns nil.")
           (release-information . nil)
           (history . nil)
           (examples . "The following example renames the dictionary created in the dictadd sample:\n\n(dictrename (namedobjdict) \"my_way_cool_dictionary\" \"An even cooler dictionary\")\n\"An even cooler dictionary\"")
           (url . "https://help.autodesk.com/cloudhelp/2023/ENU/AutoCAD-AutoLISP-Reference/files/GUID-F99779A7-2A1A-4B04-84B5-C80CC8406321.htm")
           (guid . "GUID-F99779A7-2A1A-4B04-84B5-C80CC8406321"))))
    *autolisp-reference-parts*))

(setq *autolisp-reference-entry* nil)

(setq *autolisp-reference-value* "GUID-FCB62959-7C51-41B6-8A0E-1350580F8364")

(setq *autolisp-reference-entry* (cons (cons 'guid *autolisp-reference-value*) *autolisp-reference-entry*))

(setq *autolisp-reference-value* "https://help.autodesk.com/cloudhelp/2023/ENU/AutoCAD-AutoLISP-Reference/files/GUID-FCB62959-7C51-41B6-8A0E-1350580F8364.htm")

(setq *autolisp-reference-entry* (cons (cons 'url *autolisp-reference-value*) *autolisp-reference-entry*))

(setq *autolisp-reference-value* "The following example illustrates the use of dictsearch to obtain the dictionary added in the dictadd example:\n\n(setq newdictlist (dictsearch (namedobjdict) \"my_way_cool_dictionary\"))\n((-1 . <Entity name: 1d98950>) (0 . \"DICTIONARY\") (5 . \"52\") (102 . \"{ACAD_REACTORS\")\n(330 . <Entity name: 1d98860>) (102 . \"}\") (330 . <Entity name: 1d98860>)\n(100 . \"AcDbDictionary\") (280 . 0) (281 . 1) (3 . \"DATA_RECORD_1\") (350 . <Entity name: 1d98958>))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nThe entry for the specified item, if successful; otherwise nil, if no entry is found.")

(setq *autolisp-reference-entry* (cons (cons 'return-values *autolisp-reference-value*) *autolisp-reference-entry*))

(setq *autolisp-reference-value* nil)

(setq *autolisp-reference-string* "Type: T or nil\nIf present and not nil, the dictnext entry counter is adjusted so the following dictnext call returns the entry after the one returned by this dictsearch call.")

(setq *autolisp-reference-value* (cons (cons "setnext" *autolisp-reference-string*) *autolisp-reference-value*))

(setq *autolisp-reference-string* "Type: String\nA string that specifies the item to be searched for within the dictionary.")

(setq *autolisp-reference-value* (cons (cons "symbol" *autolisp-reference-string*) *autolisp-reference-value*))

(setq *autolisp-reference-string* "Type: Ename (entity name)\nName of the dictionary being searched.")

(setq *autolisp-reference-value* (cons (cons "ename" *autolisp-reference-string*) *autolisp-reference-value*))

(setq *autolisp-reference-entry* (cons (cons 'arguments *autolisp-reference-value*) *autolisp-reference-entry*))

(setq *autolisp-reference-value* "(dictsearch ename symbol [setnext])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Symbol Table and Dictionary-Handling"))

(setq *autolisp-reference-entry* (cons (cons 'feature-groups *autolisp-reference-value*) *autolisp-reference-entry*))

(setq *autolisp-reference-value* "D")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Searches a dictionary for an item")

(setq *autolisp-reference-entry* (cons (cons 'summary *autolisp-reference-value*) *autolisp-reference-entry*))

(setq *autolisp-reference-value* "dictsearch (AutoLISP)")

(setq *autolisp-reference-entry* (cons (cons 'title *autolisp-reference-value*) *autolisp-reference-entry*))

(setq *autolisp-reference-value* "dictsearch")

(setq *autolisp-reference-entry* (cons (cons 'name *autolisp-reference-value*) *autolisp-reference-entry*))

(setq *autolisp-reference-parts* (cons (list (cons "dictsearch" *autolisp-reference-entry*)) *autolisp-reference-parts*))

(setq *autolisp-reference-parts*
  (cons
    '(("dimx_tile" .
          ((name . "dimx_tile")
           (title . "dimx_tile (AutoLISP/DCL)")
           (summary . "Retrieves the width of a tile in dialog box units")
           (source-kind . "AutoLISP/DCL")
           (alphabetic-group . "D")
           (feature-groups . ("Image Tile-Handling Functions Reference (AutoLISP/DCL)"))
           (supported-platforms . "Windows and Mac OS")
           (signature . "(dimx_tile key)")
           (arguments . (("key" . "Type: String\nValue that specifies a tile. This argument is case-sensitive.")))
           (return-values . "Type: Integer\nThe width of the tile.\nThe coordinates returned are the maximum allowed within the tile. Because coordinates are zero based, this function returns one less than the total X dimension (X-1). The dimx_tile and dimy_tile functions are provided for use with vector_image, fill_image, and slide_image, which require that you specify absolute tile coordinates.")
           (release-information . "Releases:\n- AutoCAD R12 and later on Windows\n- AutoCAD 2021 and later on Mac OS")
           (history . nil)
           (examples . "(setq tile_width (dimx_tile \"my_tile\"))")
           (url . "https://help.autodesk.com/cloudhelp/2023/ENU/AutoCAD-AutoLISP-Reference/files/GUID-AE8CC93E-1F87-4023-BC87-80584229B226.htm")
           (guid . "GUID-AE8CC93E-1F87-4023-BC87-80584229B226"))))
    *autolisp-reference-parts*))

(setq *autolisp-reference-parts*
  (cons
    '(("dimy_tile" .
          ((name . "dimy_tile")
           (title . "dimy_tile (AutoLISP/DCL)")
           (summary . "Retrieves the height of a tile in dialog box units")
           (source-kind . "AutoLISP/DCL")
           (alphabetic-group . "D")
           (feature-groups . ("Image Tile-Handling Functions Reference (AutoLISP/DCL)"))
           (supported-platforms . "Windows and Mac OS")
           (signature . "(dimy_tile key)")
           (arguments . (("key" . "Type: String\nValue that specifies a tile. This argument is case-sensitive.")))
           (return-values . "Type: Integer\nThe height of the tile.\nThe coordinates returned are the maximum allowed within the tile. Because coordinates are zero based, this function returns one less than the total Y dimension (Y-1). The dimx_tile and dimy_tile functions are provided for use with vector_image, fill_image, and slide_image, which require that you specify absolute tile coordinates.")
           (release-information . "Releases:\n- AutoCAD R12 and later on Windows\n- AutoCAD 2021 and later on Mac OS")
           (history . nil)
           (examples . "(setq tile_height (dimy_tile \"my_tile\"))")
           (url . "https://help.autodesk.com/cloudhelp/2023/ENU/AutoCAD-AutoLISP-Reference/files/GUID-FAA2950E-5374-48BF-8BCF-8B1A7C1013D8.htm")
           (guid . "GUID-FAA2950E-5374-48BF-8BCF-8B1A7C1013D8"))))
    *autolisp-reference-parts*))

(setq *autolisp-reference-parts*
  (cons
    '(("distance" .
          ((name . "distance")
           (title . "distance (AutoLISP)")
           (summary . "Returns the 3D distance between two points")
           (source-kind . "AutoLISP")
           (alphabetic-group . "D")
           (feature-groups . ("Geometric"))
           (supported-platforms . "Windows and Mac OS")
           (signature . "(distance pt1 pt2)")
           (arguments . (("pt1" . "Type: List\nA 2D or 3D point list.")
                           ("pt2" . "Type: List\nA 2D or 3D point list.")))
           (return-values . "Type: Real\nThe distance. If one or both of the supplied points is a 2D point, then distance ignores the Z coordinates of any 3D points supplied and returns the 2D distance between the points as projected into the current construction plane.")
           (release-information . nil)
           (history . nil)
           (examples . "(distance '(1.0 2.5 3.0) '(7.7 2.5 3.0))\n6.7\n\n(distance '(1.0 2.0 0.5) '(3.0 4.0 0.5))\n2.82843")
           (url . "https://help.autodesk.com/cloudhelp/2023/ENU/AutoCAD-AutoLISP-Reference/files/GUID-62F2AA98-1CE4-4E31-A2B7-E2C49A92E38F.htm")
           (guid . "GUID-62F2AA98-1CE4-4E31-A2B7-E2C49A92E38F"))))
    *autolisp-reference-parts*))

(setq *autolisp-reference-parts*
  (cons
    '(("distof" .
          ((name . "distof")
           (title . "distof (AutoLISP)")
           (summary . "Converts a string that represents a real (floating-point) value into a real value")
           (source-kind . "AutoLISP")
           (alphabetic-group . "D")
           (feature-groups . ("Conversion"))
           (supported-platforms . "Windows and Mac OS")
           (signature . "(distof str [mode])")
           (arguments . (("str" . "Type: String\nA string to be converted. The argument must be a string that distof can parse correctly according to the units specified by mode. It can be in the same form that rtos returns, or in a form that AutoCAD allows for keyboard entry.")
                           ("mode" . "Type: Integer\nThe units in which the string is currently formatted. The mode corresponds to the values allowed for the AutoCAD LUNITS system variable. Specify one of the following numbers for mode:\n1 -- Scientific\n2 -- Decimal\n3 -- Engineering (feet and decimal inches)\n4 -- Architectural (feet and fractional inches)\n5 -- Fractional")))
           (return-values . "Type: Real\nA real number, if successful; otherwise nil.\nNote: The distof function treats modes 3 and 4 the same. That is, if mode specifies 3 (engineering) or 4 (architectural) units, and string is in either of these formats, distof returns the correct real value.")
           (release-information . nil)
           (history . nil)
           (examples . "None")
           (url . "https://help.autodesk.com/cloudhelp/2023/ENU/AutoCAD-AutoLISP-Reference/files/GUID-CC0490B9-29BC-44C4-A317-5BAA34B0168E.htm")
           (guid . "GUID-CC0490B9-29BC-44C4-A317-5BAA34B0168E"))))
    *autolisp-reference-parts*))

(setq *autolisp-reference-parts*
  (cons
    '(("done_dialog" .
          ((name . "done_dialog")
           (title . "done_dialog (AutoLISP/DCL)")
           (summary . "Terminates a dialog box")
           (source-kind . "AutoLISP/DCL")
           (alphabetic-group . "D")
           (feature-groups . ("Dialog Box Opening and Closing Functions Reference (AutoLISP/DCL)"))
           (supported-platforms . "Windows and Mac OS")
           (signature . "(done_dialog [status])")
           (arguments . (("status" . "Type: Integer\nA positive integer that start_dialog will return instead of returning 1 for OK or 0 for Cancel. The meaning of any status value greater than 1 is determined by your application.")))
           (return-values . "Type: List\nA two-dimensional point that is the (X,Y) location of the dialog box when the user exited it.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-A150544E-ACE5-415F-AAB4-930E2715FDC7.htm")
           (guid . "GUID-A150544E-ACE5-415F-AAB4-930E2715FDC7"))))
    *autolisp-reference-parts*))

(setq *autolisp-reference-entry* nil)

(setq *autolisp-reference-value* "GUID-A65FBCCF-CC5D-47E8-9117-D577D9CB9D8A")

(setq *autolisp-reference-entry* (cons (cons 'guid *autolisp-reference-value*) *autolisp-reference-entry*))

(setq *autolisp-reference-value* "https://help.autodesk.com/cloudhelp/2023/ENU/AutoCAD-AutoLISP-Reference/files/GUID-A65FBCCF-CC5D-47E8-9117-D577D9CB9D8A.htm")

(setq *autolisp-reference-entry* (cons (cons 'url *autolisp-reference-value*) *autolisp-reference-entry*))

(setq *autolisp-reference-value* "The following example demonstrates how to list the available properties for a line object with the properties Delta, EndPoint, Normal, and StartPoint promoted to individual values.\n\nCommand: (setq e1 (car (entsel \"\\nSelect a line: \")))\nSelect a line:\n<Entity name: 10e2e4b20>\nCommand: (dumpAllProperties e1 1)\n\nBegin dumping object (class: AcDbLine)\nAngle (type: double)  (RO)  (LocalName: Angle) = 5.159347\nAnnotative (type: bool)  (LocalName: Annotative) = Failed to get value to get value\nArea (type: double)  (RO)  (LocalName: Area) = 0.000000\nBlockId (type: AcDbObjectId)  (RO) = Ix\nCastShadows (type: bool) = 0\nClassName (type: AcString)  (RO) =\nClosed (type: bool)  (RO)  (LocalName: Closed) = Failed to get value\nCollisionType (type: AcDb::CollisionType)  (RO) = 1\nColor (type: AcCmColor)  (LocalName: Color) = BYLAYER\nDelta/X (type: double)  (RO)  (LocalName: Delta X) = ")

(setq *autolisp-reference-value* (strcat *autolisp-reference-value* "3.028287\nDelta/Y (type: double)  (RO)  (LocalName: Delta Y) = -6.318026\nDelta/Z (type: double)  (RO)  (LocalName: Delta Z) = 0.000000\nEndParam (type: double)  (RO) = 7.006281\nEndPoint/X (type: double)  (LocalName: End X) = 23.249243\nEndPoint/Y (type: double)  (LocalName: End Y) = 11.968958\nEndPoint/Z (type: double)  (LocalName: End Z) = 0.000000\nExtensionDictionary (type: AcDbObjectId)  (RO) = Ix\nHandle (type: AcDbHandle)  (RO) = 1b2\nHasFields (type: bool)  (RO) = 0\nHasSaveVersionOverride (type: bool) = 0\nHyperlinks (type: AcDbHyperlink*)\nIsA (type: AcRxClass*)  (RO) = AcDbLine\nIsAProxy (type: bool)  (RO) = 0\nIsCancelling (type: bool)  (RO) = 0\nIsEraseStatusToggled (type: bool)  (RO) = 0\nIsErased (type: bool)  (RO) = 0\nIsModified (type: bool)  (RO) = 0\nIsModifiedGraphics (type: bool)  (RO) = 0\nIsModifiedXData (type: bool)  (RO) = 0\nIsNewObject (type: bool)  (RO) = 0\n"))

(setq *autolisp-reference-value* (strcat *autolisp-reference-value* "IsNotifyEnabled (type: bool)  (RO) = 0\nIsNotifying (type: bool)  (RO) = 0\nIsObjectIdsInFlux (type: bool)  (RO) = 0\nIsPeriodic (type: bool)  (RO) = 0\nIsPersistent (type: bool)  (RO) = 1\nIsPlanar (type: bool)  (RO) = 1\nIsReadEnabled (type: bool)  (RO) = 1\nIsReallyClosing (type: bool)  (RO) = 1\nIsTransactionResident (type: bool)  (RO) = 0\nIsUndoing (type: bool)  (RO) = 0\nIsWriteEnabled (type: bool)  (RO) = 0\nLayerId (type: AcDbObjectId)  (LocalName: Layer) = Ix\nLength (type: double)  (RO)  (LocalName: Length) = 7.006281\nLineWeight (type: AcDb::LineWeight)  (LocalName: Lineweight) = -1\nLinetypeId (type: AcDbObjectId)  (LocalName: Linetype) = Ix\nLinetypeScale (type: double)  (LocalName: Linetype scale) = 1.000000\nLocalizedName (type: AcString)  (RO) = Line\nMaterialId (type: AcDbObjectId)  (LocalName: Material) = Ix\nMergeStyle (type: AcDb::DuplicateRecordCloning)  (RO) = 1\nN"))

(setq *autolisp-reference-value* (strcat *autolisp-reference-value* "ormal/X (type: double) = 0.000000\nNormal/Y (type: double) = 0.000000\nNormal/Z (type: double) = 1.000000\nObjectId (type: AcDbObjectId)  (RO) = Ix\nOwnerId (type: AcDbObjectId)  (RO) = Ix\nPlotStyleName (type: AcString)  (LocalName: Plot style) = ByLayer\nReceiveShadows (type: bool) = 0 Failed to get value\nStartParam (type: double)  (RO) = 0.000000\nStartPoint/X (type: double)  (LocalName: Start X) = 20.220956\nStartPoint/Y (type: double)  (LocalName: Start Y) = 18.286984\nStartPoint/Z (type: double)  (LocalName: Start Z) = 0.000000\nThickness (type: double)  (LocalName: Thickness) = 0.000000\nTransparency (type: AcCmTransparency)  (LocalName: Transparency) = 0\nVisible (type: AcDb::Visibility) = 0\nEnd object dump"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Nil\nnil is returned by the function while the properties and their current values are output to the Command Line history.")

(setq *autolisp-reference-entry* (cons (cons 'return-values *autolisp-reference-value*) *autolisp-reference-entry*))

(setq *autolisp-reference-value* nil)

(setq *autolisp-reference-string* "Type: Integer\nValue expected is 0 or 1, the default is 0 when a value is not provided. When 1 is provided as the context, some property values such as Position, Normal, and StartPoint are promoted from a single value to individual X, Y, and Z values.\nFor example, the following displays the StartPoint first as not being promoted and then being as promoted:\n- Not promoted, context = 0\n- StartPoint (type: AcGePoint3d)  (LocalName: StartPoint) = 6.250000   8.750000  0.000000\n- Promoted, context = 1\n- StartPoint/X (type: double)  (LocalName: Start X) = 6.250000\n- StartPoint/Y (type: double)  (LocalName: Start Y) = 8.750000\n- StartPoint/Z (type: double)  (LocalName: Start Z) = 0.000000")

(setq *autolisp-reference-value* (cons (cons "context" *autolisp-reference-string*) *autolisp-reference-value*))

(setq *autolisp-reference-string* "Type: Ename (entity name)\nName of the entity being queried. The ename can refer to either a graphical or nongraphical entity.")

(setq *autolisp-reference-value* (cons (cons "ename" *autolisp-reference-string*) *autolisp-reference-value*))

(setq *autolisp-reference-entry* (cons (cons 'arguments *autolisp-reference-value*) *autolisp-reference-entry*))

(setq *autolisp-reference-value* "(dumpallproperties ename [context])\n\nStartPoint (type: AcGePoint3d)  (LocalName: StartPoint) = 6.250000   8.750000  0.000000\n\nStartPoint/X (type: double)  (LocalName: Start X) = 6.250000\nStartPoint/Y (type: double)  (LocalName: Start Y) = 8.750000\nStartPoint/Z (type: double)  (LocalName: Start Z) = 0.000000")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Object-Handling"))

(setq *autolisp-reference-entry* (cons (cons 'feature-groups *autolisp-reference-value*) *autolisp-reference-entry*))

(setq *autolisp-reference-value* "D")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Retrieves an entity’s supported properties")

(setq *autolisp-reference-entry* (cons (cons 'summary *autolisp-reference-value*) *autolisp-reference-entry*))

(setq *autolisp-reference-value* "dumpallproperties (AutoLISP)")

(setq *autolisp-reference-entry* (cons (cons 'title *autolisp-reference-value*) *autolisp-reference-entry*))

(setq *autolisp-reference-value* "dumpallproperties")

(setq *autolisp-reference-entry* (cons (cons 'name *autolisp-reference-value*) *autolisp-reference-entry*))

(setq *autolisp-reference-parts* (cons (list (cons "dumpallproperties" *autolisp-reference-entry*)) *autolisp-reference-parts*))

(setq *autolisp-reference-parts*
  (cons
    '(("end_image" .
          ((name . "end_image")
           (title . "end_image (AutoLISP/DCL)")
           (summary . "Ends creation of the currently active dialog box image")
           (source-kind . "AutoLISP/DCL")
           (alphabetic-group . "E")
           (feature-groups . ("Image Tile-Handling Functions Reference (AutoLISP/DCL)"))
           (supported-platforms . "Windows and Mac OS")
           (signature . "(end_image)")
           (arguments . nil)
           (return-values . "Type: nil\nAlways returns nil.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-C5DDD271-AA70-4546-9346-09C540979AC2.htm")
           (guid . "GUID-C5DDD271-AA70-4546-9346-09C540979AC2"))))
    *autolisp-reference-parts*))

(setq *autolisp-reference-parts*
  (cons
    '(("end_list" .
          ((name . "end_list")
           (title . "end_list (AutoLISP/DCL)")
           (summary . "Ends processing of the currently active dialog box list")
           (source-kind . "AutoLISP/DCL")
           (alphabetic-group . "E")
           (feature-groups . ("List Box and Pop-Up List-Handling Functions Reference (AutoLISP/DCL)"))
           (supported-platforms . "Windows and Mac OS")
           (signature . "(end_list)")
           (arguments . nil)
           (return-values . "Type: nil\nAlways returns nil.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-389C46C7-3E8A-41CA-96B6-8BD63577B763.htm")
           (guid . "GUID-389C46C7-3E8A-41CA-96B6-8BD63577B763"))))
    *autolisp-reference-parts*))

(setq *autolisp-reference-parts*
  (cons
    '(("entdel" .
          ((name . "entdel")
           (title . "entdel (AutoLISP)")
           (summary . "Deletes objects (entities) or restores previously deleted objects")
           (source-kind . "AutoLISP")
           (alphabetic-group . "E")
           (feature-groups . ("Object-Handling"))
           (supported-platforms . "Windows and Mac OS")
           (signature . "(entdel ename)")
           (arguments . (("ename" . "Type: Ename (entity name)\nName of the entity to be deleted or restored.")))
           (return-values . "Type: Ename (entity name)\nThe entity name.")
           (release-information . nil)
           (history . nil)
           (examples . "Get the name of the first entity in the drawing and assign it to variable e1:\n\n(setq e1 (entnext))\n<Entity name: 2c90520>\n\nDelete the entity named by e1:\n\n(entdel e1)\n<Entity name: 2c90520>\n\nRestore the entity named by e1:\n\n(entdel e1) <Entity name: 2c90520>")
           (url . "https://help.autodesk.com/cloudhelp/2023/ENU/AutoCAD-AutoLISP-Reference/files/GUID-AF320BD5-C83C-4EA0-983E-1EC885F5FC70.htm")
           (guid . "GUID-AF320BD5-C83C-4EA0-983E-1EC885F5FC70"))))
    *autolisp-reference-parts*))

(setq *autolisp-reference-entry* nil)

(setq *autolisp-reference-value* "GUID-12540DAE-C84B-4BDB-AEEC-DDFE5BE3C42A")

(setq *autolisp-reference-entry* (cons (cons 'guid *autolisp-reference-value*) *autolisp-reference-entry*))

(setq *autolisp-reference-value* "https://help.autodesk.com/cloudhelp/2023/ENU/AutoCAD-AutoLISP-Reference/files/GUID-12540DAE-C84B-4BDB-AEEC-DDFE5BE3C42A.htm")

(setq *autolisp-reference-entry* (cons (cons 'url *autolisp-reference-value*) *autolisp-reference-entry*))

(setq *autolisp-reference-value* "Assume that the last object created in the drawing is a line drawn from point (1,2) to point (6,5). The following example shows code that retrieves the entity name of the last object with the entlast function, and passes that name to entget:\n\n(entget (entlast))\n((-1 . <Entity name: 1bbd1d0>) (0 . \"LINE\") (330 . <Entity name: 1bbd0c8>)\n(5 . \"6A\") (100 . \"AcDbEntity\") (67 . 0) (410 . \"Model\") (8 . \"0\") (100 . \"AcDbLine\")\n(10 1.0 2.0 0.0) (11 6.0 5.0 0.0) (210 0.0 0.0 1.0))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Ename (entity name)\nAn association list containing the entity definition of ename. If you specify the optional applist argument, entget also returns the extended data associated with the specified applications. Objects in the list are assigned AutoCAD DXF™ group codes for each part of the entity data.\nNote that the DXF group codes used by AutoLISP differ slightly from the group codes in a DXF file.")

(setq *autolisp-reference-entry* (cons (cons 'return-values *autolisp-reference-value*) *autolisp-reference-entry*))

(setq *autolisp-reference-value* nil)

(setq *autolisp-reference-string* "Type: List\nA list of registered application names.")

(setq *autolisp-reference-value* (cons (cons "applist" *autolisp-reference-string*) *autolisp-reference-value*))

(setq *autolisp-reference-string* "Type: Ename (entity name)\nName of the entity being queried. The ename can refer to either a graphical or a nongraphical entity.")

(setq *autolisp-reference-value* (cons (cons "ename" *autolisp-reference-string*) *autolisp-reference-value*))

(setq *autolisp-reference-entry* (cons (cons 'arguments *autolisp-reference-value*) *autolisp-reference-entry*))

(setq *autolisp-reference-value* "(entget ename [applist])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Object-Handling"))

(setq *autolisp-reference-entry* (cons (cons 'feature-groups *autolisp-reference-value*) *autolisp-reference-entry*))

(setq *autolisp-reference-value* "E")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Retrieves an object's (entity's) definition data")

(setq *autolisp-reference-entry* (cons (cons 'summary *autolisp-reference-value*) *autolisp-reference-entry*))

(setq *autolisp-reference-value* "entget (AutoLISP)")

(setq *autolisp-reference-entry* (cons (cons 'title *autolisp-reference-value*) *autolisp-reference-entry*))

(setq *autolisp-reference-value* "entget")

(setq *autolisp-reference-entry* (cons (cons 'name *autolisp-reference-value*) *autolisp-reference-entry*))

(setq *autolisp-reference-parts* (cons (list (cons "entget" *autolisp-reference-entry*)) *autolisp-reference-parts*))

(setq *autolisp-reference-parts*
  (cons
    '(("entlast" .
          ((name . "entlast")
           (title . "entlast (AutoLISP)")
           (summary . "Returns the name of the last nondeleted main object (entity) in the drawing")
           (source-kind . "AutoLISP")
           (alphabetic-group . "E")
           (feature-groups . ("Object-Handling"))
           (supported-platforms . "Windows and Mac OS")
           (signature . "(entlast)")
           (arguments . nil)
           (return-values . "Type: Ename (entity name)\nAn entity name; otherwise nil, if there are no entities in the current drawing.")
           (release-information . nil)
           (history . nil)
           (examples . "Set variable e1 to the name of the last entity added to the drawing:\n\n(setq e1 (entlast))\n<Entity name: 2c90538>\n\nIf your application requires the name of the last nondeleted entity (main entity or subentity), define a function such as the following and call it instead of entlast.\n\n(defun lastent (/ a b)\n  (if (setq a (entlast))         Gets last main entity\n    (while (setq b (entnext a))  If subentities follow, loopsuntil there are no more\n      (setq a b)                 subentities\n    )\n  )\n  a                              Returns last main entity\n)                                or subentity")
           (url . "https://help.autodesk.com/cloudhelp/2023/ENU/AutoCAD-AutoLISP-Reference/files/GUID-75DBA9B2-034B-4377-A4E2-21D37B298D86.htm")
           (guid . "GUID-75DBA9B2-034B-4377-A4E2-21D37B298D86"))))
    *autolisp-reference-parts*))

(setq *autolisp-reference-entry* nil)

(setq *autolisp-reference-value* "GUID-D47983BA-1E5D-417D-85B8-6F3DE5F506BA")

(setq *autolisp-reference-entry* (cons (cons 'guid *autolisp-reference-value*) *autolisp-reference-entry*))

(setq *autolisp-reference-value* "https://help.autodesk.com/cloudhelp/2023/ENU/AutoCAD-AutoLISP-Reference/files/GUID-D47983BA-1E5D-417D-85B8-6F3DE5F506BA.htm")

(setq *autolisp-reference-entry* (cons (cons 'url *autolisp-reference-value*) *autolisp-reference-entry*))

(setq *autolisp-reference-value* "The following code creates a green circle (group code 62 is for color, 3 is for green), centered at (4,4) with a radius of 1. The optional layer and linetype fields have been omitted and therefore assume default values.\n\n(entmake '((0 . \"CIRCLE\") (62 . 3) (10 4.0 4.0 0.0) (40 . 1.0)))\n((0 . \"CIRCLE\") (62 . 1) (10 4.0 4.0 0.0) (40 . 1.0))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List (dotted pairs)\nIf successful, entmake returns the entity's list of definition data. If entmake is unable to create the entity, it returns nil.\nCompletion of a block definition (entmake of an endblk) returns the block's name rather than the entity data list normally returned.")

(setq *autolisp-reference-entry* (cons (cons 'return-values *autolisp-reference-value*) *autolisp-reference-entry*))

(setq *autolisp-reference-value* nil)

(setq *autolisp-reference-string* "Type: List (dotted pairs)\nEntity definition data in a format similar to that returned by the entget function. The elist argument must contain all of the information necessary to define the entity. If any required definition data is omitted, entmake returns nil and the entity is rejected. If you omit optional definition data (such as the layer), entmake uses the default value.\nThe entity type (for example, CIRCLE or LINE) must be the first or second field of the elist. If entity type is the second field, it can be preceded only by the entity name. The entmake function ignores the entity name when creating the new entity. If the elist contains an entity handle, entmake ignores that too.")

(setq *autolisp-reference-value* (cons (cons "elist" *autolisp-reference-string*) *autolisp-reference-value*))

(setq *autolisp-reference-entry* (cons (cons 'arguments *autolisp-reference-value*) *autolisp-reference-entry*))

(setq *autolisp-reference-value* "(entmake [elist])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Object-Handling"))

(setq *autolisp-reference-entry* (cons (cons 'feature-groups *autolisp-reference-value*) *autolisp-reference-entry*))

(setq *autolisp-reference-value* "E")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Creates a new entity in the drawing")

(setq *autolisp-reference-entry* (cons (cons 'summary *autolisp-reference-value*) *autolisp-reference-entry*))

(setq *autolisp-reference-value* "entmake (AutoLISP)")

(setq *autolisp-reference-entry* (cons (cons 'title *autolisp-reference-value*) *autolisp-reference-entry*))

(setq *autolisp-reference-value* "entmake")

(setq *autolisp-reference-entry* (cons (cons 'name *autolisp-reference-value*) *autolisp-reference-entry*))

(setq *autolisp-reference-parts* (cons (list (cons "entmake" *autolisp-reference-entry*)) *autolisp-reference-parts*))

(setq *autolisp-reference-parts*
  (cons
    '(("entmakex" .
          ((name . "entmakex")
           (title . "entmakex (AutoLISP)")
           (summary . "Makes a new object or entity, gives it a handle and entity name (but does not assign an owner), and then returns the new entity name")
           (source-kind . "AutoLISP")
           (alphabetic-group . "E")
           (feature-groups . ("Object-Handling"))
           (supported-platforms . "Windows and Mac OS")
           (signature . "(entmakex [elist])")
           (arguments . (("elist" . "Type: List\nEntity definition data in a format similar to that returned by the entget function. The elist argument must contain all of the information necessary to define the entity. If any required definition data is omitted, entmakex returns nil and the entity is rejected. If you omit optional definition data (such as the layer), entmakex uses the default value.")))
           (return-values . "Type: Ename (entity name)\nIf successful, entmakex returns the name of the entity created. If entmakex is unable to create the entity, the function returns nil.")
           (release-information . nil)
           (history . nil)
           (examples . "(entmakex '((0 . \"CIRCLE\") (62 . 1) (10 4.0 3.0 0.0) (40 . 1.0)))\n<Entity name: 1d45558>")
           (url . "https://help.autodesk.com/cloudhelp/2023/ENU/AutoCAD-AutoLISP-Reference/files/GUID-3F9A2EB2-082D-49DD-8EFD-DAD8F6E9AA6A.htm")
           (guid . "GUID-3F9A2EB2-082D-49DD-8EFD-DAD8F6E9AA6A"))))
    *autolisp-reference-parts*))

(setq *autolisp-reference-entry* nil)

(setq *autolisp-reference-value* "GUID-C7D27797-247E-49B9-937C-0D8C58F4C832")

(setq *autolisp-reference-entry* (cons (cons 'guid *autolisp-reference-value*) *autolisp-reference-entry*))

(setq *autolisp-reference-value* "https://help.autodesk.com/cloudhelp/2023/ENU/AutoCAD-AutoLISP-Reference/files/GUID-C7D27797-247E-49B9-937C-0D8C58F4C832.htm")

(setq *autolisp-reference-entry* (cons (cons 'url *autolisp-reference-value*) *autolisp-reference-entry*))

(setq *autolisp-reference-value* "The following sequence of commands obtains the properties of an entity, and then modifies the entity.\n\nSet the en1 variable to the name of the first entity in the drawing:\n\n(setq en1 (entnext))\n<Entity name: 2c90520>\n\nSet a variable named ed to the entity data of entity en1:\n\n(setq ed (entget en1))\n((-1 . <Entity name: 2c90520>) (0 . \"CIRCLE\") (5 . \"4C\") (100 . \"AcDbEntity\") (67 . 0) (8 . \"0\")\n(100 . \"AcDbCircle\") (10 3.45373 6.21635 0.0) (40 . 2.94827) (210 0.0 0.0 1.0))\n\nChanges the layer group in ed from layer 0 to layer 1:\n\n(setq ed (subst (cons 8 \"1\") (assoc 8 ed) ed ))\n((-1 . <Entity name: 2c90520>) (0 . \"CIRCLE\") (5 . \"4C\") (100 . \"AcDbEntity\") (67 . 0) (8 . \"1\")\n(100 . \"AcDbCircle\") (10 3.45373 6.21635 0.0) (40 . 2.94827) (210 0.0 0.0 1.0))\n\nModify the layer of the en1 entity in the drawing:\n\n(entmod ed)((-1 . <Entity name: 2c90520>) (0 ")

(setq *autolisp-reference-value* (strcat *autolisp-reference-value* ". \"CIRCLE\") (5 . \"4C\")\n(100 . \"AcDbEntity\") (67 . 0) (8 . \"1\") (100 . \"AcDbCircle\") (10 3.45373 6.21635 0.0) (40 . 2.94827) (210 0.0 0.0 1.0))"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nIf successful, entmod returns the elist supplied to it. If entmod is unable to modify the specified entity, the function returns nil.")

(setq *autolisp-reference-entry* (cons (cons 'return-values *autolisp-reference-value*) *autolisp-reference-entry*))

(setq *autolisp-reference-value* nil)

(setq *autolisp-reference-string* "Type: List\nEntity definition data in a format similar to that returned by the entget function.\nFor entity fields with floating-point values (such as thickness), entmod accepts integer values and converts them to floating point. Similarly, if you supply a floating-point value for an integer entity field (such as color number), entmod truncates it and converts it to an integer.")

(setq *autolisp-reference-value* (cons (cons "elist" *autolisp-reference-string*) *autolisp-reference-value*))

(setq *autolisp-reference-entry* (cons (cons 'arguments *autolisp-reference-value*) *autolisp-reference-entry*))

(setq *autolisp-reference-value* "(entmod elist)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Object-Handling"))

(setq *autolisp-reference-entry* (cons (cons 'feature-groups *autolisp-reference-value*) *autolisp-reference-entry*))

(setq *autolisp-reference-value* "E")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Modifies the definition data of an object (entity)")

(setq *autolisp-reference-entry* (cons (cons 'summary *autolisp-reference-value*) *autolisp-reference-entry*))

(setq *autolisp-reference-value* "entmod (AutoLISP)")

(setq *autolisp-reference-entry* (cons (cons 'title *autolisp-reference-value*) *autolisp-reference-entry*))

(setq *autolisp-reference-value* "entmod")

(setq *autolisp-reference-entry* (cons (cons 'name *autolisp-reference-value*) *autolisp-reference-entry*))

(setq *autolisp-reference-parts* (cons (list (cons "entmod" *autolisp-reference-entry*)) *autolisp-reference-parts*))

(setq *autolisp-reference-parts*
  (cons
    '(("entnext" .
          ((name . "entnext")
           (title . "entnext (AutoLISP)")
           (summary . "Returns the name of the next object (entity) in the drawing")
           (source-kind . "AutoLISP")
           (alphabetic-group . "E")
           (feature-groups . ("Object-Handling"))
           (supported-platforms . "Windows and Mac OS")
           (signature . "(entnext [ename])")
           (arguments . (("ename" . "Type: Ename (entity name)\nThe name of an existing entity.")))
           (return-values . "Type: Ename (entity name) or nil\nIf entnext is called with no arguments, it returns the entity name of the first nondeleted entity in the database. If an ename argument is supplied to entnext, the function returns the entity name of the first nondeleted entity following ename in the database. If there is no next entity in the database, it returns nil. The entnext function returns both main entities and subentities.")
           (release-information . nil)
           (history . nil)
           (examples . "(setq e1 (entnext))    ; Sets e1 to the name of the first entity in  the  drawing\n\n(setq e2 (entnext e1)) ; Sets e2 to the name of the entity following e1")
           (url . "https://help.autodesk.com/cloudhelp/2023/ENU/AutoCAD-AutoLISP-Reference/files/GUID-65924CF5-0C51-4E36-8B38-7A5513951A04.htm")
           (guid . "GUID-65924CF5-0C51-4E36-8B38-7A5513951A04"))))
    *autolisp-reference-parts*))

(setq *autolisp-reference-parts*
  (cons
    '(("entsel" .
          ((name . "entsel")
           (title . "entsel (AutoLISP)")
           (summary . "Prompts the user to select a single object (entity) by specifying a point")
           (source-kind . "AutoLISP")
           (alphabetic-group . "E")
           (feature-groups . ("User Input"))
           (supported-platforms . "Windows and Mac OS")
           (signature . "(entsel [msg])")
           (arguments . (("msg" . "Type: String\nA prompt string to be displayed to users. If omitted, entsel prompts with the message, \"Select object.\"")))
           (return-values . "Type: List or nil\nA list whose first element is the entity name of the chosen object and whose second element is the coordinates (in terms of the current UCS) of the point used to pick the object.\nThe pick point returned by entsel does not represent a point that lies on the selected object. The point returned is the location of the crosshairs at the time of selection. The relationship between the pick point and the object will vary depending on the size of the pickbox and the current zoom scale.")
           (release-information . nil)
           (history . nil)
           (examples . "The following AutoCAD command sequence illustrates the use of the entsel function and the list returned:\n\nCommand: line\n\nFrom point: 1,1\n\nTo point: 6,6\n\nTo point: Press Enter\n\nCommand: (setq e (entsel \"\\nSelect an object: \"))\n\nSelect an object: 3,3\n\n(<Entity name: 60000014> (3.0 3.0 0.0))")
           (url . "https://help.autodesk.com/cloudhelp/2023/ENU/AutoCAD-AutoLISP-Reference/files/GUID-9D4CF74D-8B8B-4D66-A952-564AFBA254E7.htm")
           (guid . "GUID-9D4CF74D-8B8B-4D66-A952-564AFBA254E7"))))
    *autolisp-reference-parts*))

(setq *autolisp-reference-parts*
  (cons
    '(("entupd" .
          ((name . "entupd")
           (title . "entupd (AutoLISP)")
           (summary . "Updates the screen image of an object (entity)")
           (source-kind . "AutoLISP")
           (alphabetic-group . "E")
           (feature-groups . ("Object-Handling"))
           (supported-platforms . "Windows and Mac OS")
           (signature . "(entupd ename)")
           (arguments . (("ename" . "Type: Ename (entity name)\nThe name of the entity to be updated on the screen.")))
           (return-values . "Type: Ename (entity name) or nil\nThe updated entity; otherwise nil, if nothing was updated.")
           (release-information . nil)
           (history . nil)
           (examples . "Assuming that the first entity in the drawing is a 3D polyline with several vertices, the following code modifies and redisplays the polyline:\n\n(setq e1 (entnext))       ; Sets e1 to the polyline's entity name\n(setq e2 (entnext e1))    ; Sets e2 to its first vertex\n(setq ed (entget e2))     ; Sets ed to the vertex data\n(setq ed\n  (subst '(10 1.0 2.0)\n    (assoc 10 ed)         ; Changes the vertex's location in ed\n    ed                    ; to point (1,2)\n  )\n)\n(entmod ed)               ; Moves the vertex in the drawing\n(entupd e1)               ; Regenerates the polyline entity e1")
           (url . "https://help.autodesk.com/cloudhelp/2023/ENU/AutoCAD-AutoLISP-Reference/files/GUID-78313F48-676D-49D7-842A-288DD347A783.htm")
           (guid . "GUID-78313F48-676D-49D7-842A-288DD347A783"))))
    *autolisp-reference-parts*))

(setq *autolisp-reference-parts*
  (cons
    '(("eq" .
          ((name . "eq")
           (title . "eq (AutoLISP)")
           (summary . "Determines whether two expressions are identical")
           (source-kind . "AutoLISP")
           (alphabetic-group . "E")
           (feature-groups . ("Equality and Conditional"))
           (supported-platforms . "Windows and Mac OS")
           (signature . "(eq expr1 expr2)")
           (arguments . (("expr1" . "Type: Integer, Real, String, List, Ename (entity name), T, or nil\nThe expression to be compared.")
                           ("expr2" . "Type: Integer, Real, String, List, Ename (entity name), T, or nil\nThe expression to compare with expr1.")))
           (return-values . "Type: T or nil\nT if the two expressions are identical; otherwise nil.")
           (release-information . nil)
           (history . nil)
           (examples . "Given the following assignments:\n\n(setq f1 '(a b c))\n(setq f2 '(a b c))\n(setq f3 f2)\n\nCompare f1 and f3:\n\n(eq f1 f3)\nnil\n\neq returns nil because f1 and f3, while containing the same value, do not refer to the same list.\n\nCompare f3 and f2:\n\n(eq f3 f2)\nT\n\neq returns T because f3 and f2 refer to the same list.")
           (url . "https://help.autodesk.com/cloudhelp/2023/ENU/AutoCAD-AutoLISP-Reference/files/GUID-BC81B391-48BF-401E-80D0-05A1B578A0FF.htm")
           (guid . "GUID-BC81B391-48BF-401E-80D0-05A1B578A0FF"))))
    *autolisp-reference-parts*))

(setq *autolisp-reference-entry* nil)

(setq *autolisp-reference-value* "GUID-7E85CB8F-B4DA-42F3-ABD3-89342A11EF9B")

(setq *autolisp-reference-entry* (cons (cons 'guid *autolisp-reference-value*) *autolisp-reference-entry*))

(setq *autolisp-reference-value* "https://help.autodesk.com/cloudhelp/2023/ENU/AutoCAD-AutoLISP-Reference/files/GUID-7E85CB8F-B4DA-42F3-ABD3-89342A11EF9B.htm")

(setq *autolisp-reference-entry* (cons (cons 'url *autolisp-reference-value*) *autolisp-reference-entry*))

(setq *autolisp-reference-value* "Given the following assignments:\n\n(setq f1 '(a b c))\n(setq f2 '(a b c))\n(setq f3 f2)\n(setq a 1.123456)\n(setq b 1.123457)\n\nCompare f1 to f3:\n\n(equal f1 f3)\nT\n\nCompare f3 to f2:\n\n(equal f3 f2)\nT\n\nCompare a to b:\n\n(equal a b)\nnil\n\nThe a and b variables differ by .000001. Compare a to b:, with fuzz argument of .000001:\n\n(equal a b 0.000001)\nT\n\nThe a and b variables differ by an amount equal to the specified fuzz factor, so equal considers the variables equal.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nT if the two expressions are equal (evaluate to the same value); otherwise nil.")

(setq *autolisp-reference-entry* (cons (cons 'return-values *autolisp-reference-value*) *autolisp-reference-entry*))

(setq *autolisp-reference-value* nil)

(setq *autolisp-reference-string* "Type: Integer or Real\nA real number defining the maximum amount by which expr1 and expr2 can differ and still be considered equal.")

(setq *autolisp-reference-value* (cons (cons "fuzz" *autolisp-reference-string*) *autolisp-reference-value*))

(setq *autolisp-reference-string* "Type: Integer, Real, String, List, Ename (entity name), T, or nil\nThe expression to compare with expr1.")

(setq *autolisp-reference-value* (cons (cons "expr2" *autolisp-reference-string*) *autolisp-reference-value*))

(setq *autolisp-reference-string* "Type: Integer, Real, String, List, Ename (entity name), T, or nil\nThe expression to be compared.")

(setq *autolisp-reference-value* (cons (cons "expr1" *autolisp-reference-string*) *autolisp-reference-value*))

(setq *autolisp-reference-entry* (cons (cons 'arguments *autolisp-reference-value*) *autolisp-reference-entry*))

(setq *autolisp-reference-value* "(equal expr1 expr2 [fuzz])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Equality and Conditional"))

(setq *autolisp-reference-entry* (cons (cons 'feature-groups *autolisp-reference-value*) *autolisp-reference-entry*))

(setq *autolisp-reference-value* "E")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Determines whether two expressions are equal")

(setq *autolisp-reference-entry* (cons (cons 'summary *autolisp-reference-value*) *autolisp-reference-entry*))

(setq *autolisp-reference-value* "equal (AutoLISP)")

(setq *autolisp-reference-entry* (cons (cons 'title *autolisp-reference-value*) *autolisp-reference-entry*))

(setq *autolisp-reference-value* "equal")

(setq *autolisp-reference-entry* (cons (cons 'name *autolisp-reference-value*) *autolisp-reference-entry*))

(setq *autolisp-reference-parts* (cons (list (cons "equal" *autolisp-reference-entry*)) *autolisp-reference-parts*))

(setq *autolisp-reference-parts*
  (cons
    '(("eval" .
          ((name . "eval")
           (title . "eval (AutoLISP)")
           (summary . "Returns the result of evaluating an AutoLISP expression")
           (source-kind . "AutoLISP")
           (alphabetic-group . "E")
           (feature-groups . ("Function-Handling"))
           (supported-platforms . "Windows and Mac OS")
           (signature . "(eval expr)")
           (arguments . (("expr" . "Type: Integer, Real, String, List, Symbol, Ename (entity name), T, or nil\nThe expression to be evaluated.")))
           (return-values . "Type: Integer, Real, String, List, Symbol, Ename (entity name), T, or nil\nThe result of the expression, after evaluation.")
           (release-information . nil)
           (history . nil)
           (examples . "First, set some variables:\n\n(setq a 123)\n123\n\n(setq b 'a)\nA\n\nNow evaluate some expressions:\n\n(eval 4.0)\n4.0\n\n(eval (abs -10))\n10\n\n(eval a)\n123\n\n(eval b)\n123")
           (url . "https://help.autodesk.com/cloudhelp/2023/ENU/AutoCAD-AutoLISP-Reference/files/GUID-D9B3E6CC-A982-4040-AE6E-6FD63D6C54D0.htm")
           (guid . "GUID-D9B3E6CC-A982-4040-AE6E-6FD63D6C54D0"))))
    *autolisp-reference-parts*))

(setq *autolisp-reference-parts*
  (cons
    '(("exit" .
          ((name . "exit")
           (title . "exit (AutoLISP)")
           (summary . "Forces the current application to quit")
           (source-kind . "AutoLISP")
           (alphabetic-group . "E")
           (feature-groups . ("Error-Handling"))
           (supported-platforms . "Windows and Mac OS")
           (signature . "(exit)")
           (arguments . nil)
           (return-values . "Type: nil\nIf exit is called, it outputs the error message quit/exit abort and returns to the AutoCAD Command prompt.")
           (release-information . nil)
           (history . nil)
           (examples . "N/A")
           (url . "https://help.autodesk.com/cloudhelp/2023/ENU/AutoCAD-AutoLISP-Reference/files/GUID-677B9EC8-C35D-4736-AE59-1BDB12E540AF.htm")
           (guid . "GUID-677B9EC8-C35D-4736-AE59-1BDB12E540AF"))))
    *autolisp-reference-parts*))

(setq *autolisp-reference-parts*
  (cons
    '(("exp" .
          ((name . "exp")
           (title . "exp (AutoLISP)")
           (summary . "Returns the constant e (a real number) raised to a specified power (the natural antilog)")
           (source-kind . "AutoLISP")
           (alphabetic-group . "E")
           (feature-groups . ("Arithmetic"))
           (supported-platforms . "Windows and Mac OS")
           (signature . "(exp num)")
           (arguments . (("num" . "Type: Integer or Real\nA numeric value.")))
           (return-values . "Type: Real\nA numeric value, raised to its natural antilogarithm.")
           (release-information . nil)
           (history . nil)
           (examples . "(exp 1.0)\n2.71828\n\n(exp 2.2)\n9.02501\n\n(exp -0.4)\n0.67032")
           (url . "https://help.autodesk.com/cloudhelp/2023/ENU/AutoCAD-AutoLISP-Reference/files/GUID-FD0C918B-A162-4939-9F4E-FFE8863C3FC8.htm")
           (guid . "GUID-FD0C918B-A162-4939-9F4E-FFE8863C3FC8"))))
    *autolisp-reference-parts*))

(setq *autolisp-reference-parts*
  (cons
    '(("expand" .
          ((name . "expand")
           (title . "expand (AutoLISP)")
           (summary . "Allocates additional memory for AutoLISP")
           (source-kind . "AutoLISP")
           (alphabetic-group . "E")
           (feature-groups . ("Memory Management"))
           (supported-platforms . "Windows and Mac OS")
           (signature . "(expand n-expand)")
           (arguments . (("n-expand" . "Type: Integer\nAn number indicating the amount of additional memory to be allocated. Memory is allocated as follows:\n- n-alloc\n- free symbols\n- n-alloc\n- free strings\n- n-alloc\n- free usubrs\n- n-alloc\n- free reals\n- n-alloc\n- *\n- n-expand\n- cons cells\nwhere n-alloc is the current segment size.")))
           (return-values . "Type: Integer\nA number indicating the number of free conses divided by n-alloc.")
           (release-information . nil)
           (history . nil)
           (examples . "Set the segment size to 100:\n\n(alloc 100)\n1000\n\nAllocate memory for two additional segments:\n\n(expand 2)\n82\n\nThis ensures that AutoLISP now has memory available for at least 200 additional symbols, strings, usubrs and reals each, and 8200 free conses.")
           (url . "https://help.autodesk.com/cloudhelp/2023/ENU/AutoCAD-AutoLISP-Reference/files/GUID-48C99C97-176D-4D9C-91E2-31B3C67D6EC9.htm")
           (guid . "GUID-48C99C97-176D-4D9C-91E2-31B3C67D6EC9"))))
    *autolisp-reference-parts*))

(setq *autolisp-reference-parts*
  (cons
    '(("expt" .
          ((name . "expt")
           (title . "expt (AutoLISP)")
           (summary . "Returns a number raised to a specified power")
           (source-kind . "AutoLISP")
           (alphabetic-group . "E")
           (feature-groups . ("Arithmetic"))
           (supported-platforms . "Windows and Mac OS")
           (signature . "(expt number power)")
           (arguments . (("number" . "Type: Integer or Real\nAny number.")
                           ("power" . "Type: Integer or Real\nThe power to raise number to.")))
           (return-values . "Type: Integer or Real\nIf both arguments are integers, the result is an integer; otherwise, the result is a real.")
           (release-information . nil)
           (history . nil)
           (examples . "(expt 2 4)\n16\n\n(expt 3.0 2.0)\n9.0")
           (url . "https://help.autodesk.com/cloudhelp/2023/ENU/AutoCAD-AutoLISP-Reference/files/GUID-FCAC3150-7491-43DB-8042-37EDE3791A96.htm")
           (guid . "GUID-FCAC3150-7491-43DB-8042-37EDE3791A96"))))
    *autolisp-reference-parts*))

(setq *autolisp-reference-entry* nil)

(setq *autolisp-reference-value* "GUID-1C95F5E1-C063-4334-A296-40E7E123F66C")

(setq *autolisp-reference-entry* (cons (cons 'guid *autolisp-reference-value*) *autolisp-reference-entry*))

(setq *autolisp-reference-value* "https://help.autodesk.com/cloudhelp/2023/ENU/AutoCAD-AutoLISP-Reference/files/GUID-1C95F5E1-C063-4334-A296-40E7E123F66C.htm")

(setq *autolisp-reference-entry* (cons (cons 'url *autolisp-reference-value*) *autolisp-reference-entry*))

(setq *autolisp-reference-value* "(setq color -2) ;; color of AutoCAD drawing area\n(fill_image\n  0\n  0\n  (dimx_tile \"slide_tile\")\n  (dimy_tile \"slide_tile\")\n  color\n)\n(end_image)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* "Releases:\n- AutoCAD R12 and later on Windows\n- AutoCAD 2021 and later on Mac OS")

(setq *autolisp-reference-entry* (cons (cons 'release-information *autolisp-reference-value*) *autolisp-reference-entry*))

(setq *autolisp-reference-value* "Type: Integer\nA numeric value representing the fill color.")

(setq *autolisp-reference-entry* (cons (cons 'return-values *autolisp-reference-value*) *autolisp-reference-entry*))

(setq *autolisp-reference-value* nil)

(setq *autolisp-reference-string* "Type: Integer\nAn AutoCAD color number, or one of the logical color numbers shown in the following table:")

(setq *autolisp-reference-value* (cons (cons "color" *autolisp-reference-string*) *autolisp-reference-value*))

(setq *autolisp-reference-string* "Type: Integer\nWidth of the fill area (in pixels), relative to y1.")

(setq *autolisp-reference-value* (cons (cons "height" *autolisp-reference-string*) *autolisp-reference-value*))

(setq *autolisp-reference-string* "Type: Integer\nWidth of the fill area (in pixels), relative to x1.")

(setq *autolisp-reference-value* (cons (cons "width" *autolisp-reference-string*) *autolisp-reference-value*))

(setq *autolisp-reference-string* "Type: Integer\nY coordinate of upper-left corner. Must be a positive value.")

(setq *autolisp-reference-value* (cons (cons "y1" *autolisp-reference-string*) *autolisp-reference-value*))

(setq *autolisp-reference-string* "Type: Integer\nX coordinate of the upper-left corner of the rectangle located at (x1,y1). Must be a positive value.")

(setq *autolisp-reference-value* (cons (cons "x1" *autolisp-reference-string*) *autolisp-reference-value*))

(setq *autolisp-reference-entry* (cons (cons 'arguments *autolisp-reference-value*) *autolisp-reference-entry*))

(setq *autolisp-reference-value* "(fill_image x1 y1 width height color)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Image Tile-Handling Functions Reference (AutoLISP/DCL)"))

(setq *autolisp-reference-entry* (cons (cons 'feature-groups *autolisp-reference-value*) *autolisp-reference-entry*))

(setq *autolisp-reference-value* "F")

(setq *autolisp-reference-entry* (cons (cons 'alphabetic-group *autolisp-reference-value*) *autolisp-reference-entry*))

(setq *autolisp-reference-value* "AutoLISP/DCL")

(setq *autolisp-reference-entry* (cons (cons 'source-kind *autolisp-reference-value*) *autolisp-reference-entry*))

(setq *autolisp-reference-value* "Draws a filled rectangle in the currently active dialog box image tile")

(setq *autolisp-reference-entry* (cons (cons 'summary *autolisp-reference-value*) *autolisp-reference-entry*))

(setq *autolisp-reference-value* "fill_image (AutoLISP/DCL)")

(setq *autolisp-reference-entry* (cons (cons 'title *autolisp-reference-value*) *autolisp-reference-entry*))

(setq *autolisp-reference-value* "fill_image")

(setq *autolisp-reference-entry* (cons (cons 'name *autolisp-reference-value*) *autolisp-reference-entry*))

(setq *autolisp-reference-parts* (cons (list (cons "fill_image" *autolisp-reference-entry*)) *autolisp-reference-parts*))

(setq *autolisp-reference-entry* nil)

(setq *autolisp-reference-value* "GUID-D671F67D-F92B-41FF-B9FA-A48EF52CF607")

(setq *autolisp-reference-entry* (cons (cons 'guid *autolisp-reference-value*) *autolisp-reference-entry*))

(setq *autolisp-reference-value* "https://help.autodesk.com/cloudhelp/2023/ENU/AutoCAD-AutoLISP-Reference/files/GUID-D671F67D-F92B-41FF-B9FA-A48EF52CF607.htm")

(setq *autolisp-reference-entry* (cons (cons 'url *autolisp-reference-value*) *autolisp-reference-entry*))

(setq *autolisp-reference-value* "Windows\n\nIf the current directory is /MyUtilities/lsp and it contains the file abc.lsp, the following function call retrieves the path name:\n(findfile \"abc.lsp\")\n\"C:\\\\MyUtilities\\\\lsp\\\\abc.lsp\"\nIf you are editing a drawing in the /My Utilities/Support directory, and the ACAD environment variable is set to /My Utilities/Support, and the file xyz.txt exists only in the /My Utilities/Support directory, then the following command retrieves the path name:\n(findfile \"xyz.txt\")\n\"C:\\\\My Utilities\\\\Support\\\\xyz.txt\"\nIf the file nosuch is not present in any of the directories on the library or trusted search paths, findfile returns nil:\n(findfile \"nosuch\")\nnil\n\nMac OS\n\nIf the current directory is /MyUtilities/lsp and it contains the file abc.lsp, the following function call retrieves the path name:\n(findfile \"abc.lsp\")\n\"/MyUtilities/Lsp/abc.lsp\"\nIf you ar")

(setq *autolisp-reference-value* (strcat *autolisp-reference-value* "e editing a drawing in the /My Utilities/Support directory, and the ACAD environment variable is set to /My Utilities/Support, and the file xyz.txt exists only in the /My Utilities/Support directory, then the following command retrieves the path name:\n(findfile \"xyz.txt\")\n\"/MyUtilities/Support/xyz.txt\"\nCommand:\nIf the file nosuch is not present in any of the directories on the library or trusted search paths, findfile returns nil:\n(findfile \"nosuch\")\nnil"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String or nil\nA string containing the fully qualified file name; otherwise nil, if the specified file or directory is not found.\nThe file name returned by findfile is suitable for use with the open function.")

(setq *autolisp-reference-entry* (cons (cons 'return-values *autolisp-reference-value*) *autolisp-reference-entry*))

(setq *autolisp-reference-value* nil)

(setq *autolisp-reference-string* "Type: String\nName of the file or directory to be searched for.")

(setq *autolisp-reference-value* (cons (cons "filename" *autolisp-reference-string*) *autolisp-reference-value*))

(setq *autolisp-reference-entry* (cons (cons 'arguments *autolisp-reference-value*) *autolisp-reference-entry*))

(setq *autolisp-reference-value* "(findfile filename)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "F")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Searches the AutoCAD library and trusted paths for the specified file or directory")

(setq *autolisp-reference-entry* (cons (cons 'summary *autolisp-reference-value*) *autolisp-reference-entry*))

(setq *autolisp-reference-value* "findfile (AutoLISP)")

(setq *autolisp-reference-entry* (cons (cons 'title *autolisp-reference-value*) *autolisp-reference-entry*))

(setq *autolisp-reference-value* "findfile")

(setq *autolisp-reference-entry* (cons (cons 'name *autolisp-reference-value*) *autolisp-reference-entry*))

(setq *autolisp-reference-parts* (cons (list (cons "findfile" *autolisp-reference-entry*)) *autolisp-reference-parts*))

(setq *autolisp-reference-parts*
  (cons
    '(("findtrustedfile" .
          ((name . "findtrustedfile")
           (title . "findtrustedfile (AutoLISP)")
           (summary . "Searches the AutoCAD trusted locations for the specified file")
           (source-kind . "AutoLISP")
           (alphabetic-group . "F")
           (feature-groups . ("File-Handling"))
           (supported-platforms . "Windows only")
           (signature . "(findtrustedfile filename)")
           (arguments . (("filename" . "Type: String\nName of the file to be searched for.")))
           (return-values . "Type: String or nil\nA string containing the fully qualified file name; otherwise nil, if the specified file is not found.")
           (release-information . nil)
           (history . nil)
           (examples . "If the trusted locations and support search file paths contains C:\\myapps, and abc.lsp is contained in the path, the function retrieves the path name:\n\n(findtrustedfile \"abc.lsp\")\n\"C:\\\\myapps\\\\abc.lsp\"\n\nIf the folder in which abc.lsp is not present in both the trusted locations and support search file paths, findtrustedfile returns nil.\n\n(findtrustedfile \"abc.lsp\")\nnil")
           (url . "https://help.autodesk.com/cloudhelp/2023/ENU/AutoCAD-AutoLISP-Reference/files/GUID-456F421A-DED1-4A87-9D4A-8434D1E997E1.htm")
           (guid . "GUID-456F421A-DED1-4A87-9D4A-8434D1E997E1"))))
    *autolisp-reference-parts*))

(setq *autolisp-reference-parts*
  (cons
    '(("fix" .
          ((name . "fix")
           (title . "fix (AutoLISP)")
           (summary . "Returns the conversion of a real number into the nearest smaller integer")
           (source-kind . "AutoLISP")
           (alphabetic-group . "F")
           (feature-groups . ("Arithmetic"))
           (supported-platforms . "Windows and Mac OS")
           (signature . "(fix number)")
           (arguments . (("number" . "Type: Integer or Real\nA numeric value.")))
           (return-values . "Type: Integer\nThe integer derived from number.\nIf number is larger than the largest possible integer (+2,147,483,647 or -2,147,483,648 on a 32-bit platform), fix returns a truncated real (although integers transferred between AutoLISP and AutoCAD are restricted to 16-bit values).")
           (release-information . nil)
           (history . nil)
           (examples . "(fix 3)\n3\n\n(fix 3.7)\n3")
           (url . "https://help.autodesk.com/cloudhelp/2023/ENU/AutoCAD-AutoLISP-Reference/files/GUID-93B5F13B-348E-49E0-A116-0861684506D5.htm")
           (guid . "GUID-93B5F13B-348E-49E0-A116-0861684506D5"))))
    *autolisp-reference-parts*))

(setq *autolisp-reference-parts*
  (cons
    '(("float" .
          ((name . "float")
           (title . "float (AutoLISP)")
           (summary . "Returns the conversion of a number into a real number")
           (source-kind . "AutoLISP")
           (alphabetic-group . "F")
           (feature-groups . ("Arithmetic"))
           (supported-platforms . "Windows and Mac OS")
           (signature . "(float number)")
           (arguments . (("number" . "Type: Integer or Real\nA numeric value.")))
           (return-values . "Type: Real\nThe real number derived from number.")
           (release-information . nil)
           (history . nil)
           (examples . "(float 3)\n3.0\n\n(float 3.75)\n3.75")
           (url . "https://help.autodesk.com/cloudhelp/2023/ENU/AutoCAD-AutoLISP-Reference/files/GUID-93808F66-808C-49F7-9303-F12C55296080.htm")
           (guid . "GUID-93808F66-808C-49F7-9303-F12C55296080"))))
    *autolisp-reference-parts*))

(setq *autolisp-reference-parts*
  (cons
    '(("foreach" .
          ((name . "foreach")
           (title . "foreach (AutoLISP)")
           (summary . "Evaluates expressions for all members of a list")
           (source-kind . "AutoLISP")
           (alphabetic-group . "F")
           (feature-groups . ("List Manipulation"))
           (supported-platforms . "Windows and Mac OS")
           (signature . "(foreach name list [expr...])")
           (arguments . (("name" . "Type: Symbol\nVariable that each element in the list will be assigned to.")
                           ("list" . "Type: List\nList to be stepped through and evaluated.")
                           ("expr" . "Type: List\nExpression to be evaluated for each element in list.")))
           (return-values . "Type: Integer, Real, String, List, Ename (entity name), T, or nil\nThe result of the last expr evaluated. If no expr is specified, foreach returns nil.")
           (release-information . nil)
           (history . nil)
           (examples . "Print each element in a list:\n\n(foreach n '(a b c) (print n))\nA\nB\nC C\n\nforeach prints each element in the list and returns C, the last element. This command is equivalent to the following sequence of commands, except that foreach returns the result of only the last expression evaluated:\n\n(print a)\n(print b)\n(print c)")
           (url . "https://help.autodesk.com/cloudhelp/2023/ENU/AutoCAD-AutoLISP-Reference/files/GUID-BE6A23C4-4E18-45A6-854E-2DE9574A6925.htm")
           (guid . "GUID-BE6A23C4-4E18-45A6-854E-2DE9574A6925"))))
    *autolisp-reference-parts*))

(setq *autolisp-reference-parts*
  (cons
    '(("function" .
          ((name . "function")
           (title . "function (AutoLISP/Visual LISP IDE)")
           (summary . "Tells the Visual LISP compiler to link and optimize an argument as if it were a built-in function")
           (source-kind . "AutoLISP/Visual LISP IDE")
           (alphabetic-group . "F")
           (feature-groups . nil)
           (supported-platforms . "Windows only")
           (signature . "(function symbol | lambda-expr)")
           (arguments . (("symbol" . "Type: Symbol\nA symbol naming a function.")
                           ("lambda-expr" . "Type: Subroutine or List\nAn expression of the following form:\n(LAMBDA arguments {S-expression}*)")))
           (return-values . "The result of the evaluated expression.")
           (release-information . nil)
           (history . nil)
           (examples . "The Visual LISP compiler cannot optimize the quoted lambda expression in the following code:\n\n(mapcar\n  '(lambda (x) (* x x))\n       '(1 2 3))\n\nAfter adding the function function to the expression, the compiler can optimize the lambda expression. For example:\n\n(mapcar\n   (function (lambda (x) (* x x)))\n      '(1 2 3))")
           (url . "https://help.autodesk.com/cloudhelp/2023/ENU/AutoCAD-AutoLISP-Reference/files/GUID-CF7E5870-561F-42DB-B134-CCD41EF93A25.htm")
           (guid . "GUID-CF7E5870-561F-42DB-B134-CCD41EF93A25"))))
    *autolisp-reference-parts*))

(setq *autolisp-reference-parts*
  (cons
    '(("gc" .
          ((name . "gc")
           (title . "gc (AutoLISP)")
           (summary . "Forces a garbage collection, which frees up unused memory")
           (source-kind . "AutoLISP")
           (alphabetic-group . "G")
           (feature-groups . ("Memory Management"))
           (supported-platforms . "Windows and Mac OS")
           (signature . "(gc)")
           (arguments . nil)
           (return-values . "Type: nil\nAlways returns nil.")
           (release-information . nil)
           (history . nil)
           (examples . nil)
           (url . "https://help.autodesk.com/cloudhelp/2023/ENU/AutoCAD-AutoLISP-Reference/files/GUID-6CABB3AF-9BED-4237-8A44-D36123246BF4.htm")
           (guid . "GUID-6CABB3AF-9BED-4237-8A44-D36123246BF4"))))
    *autolisp-reference-parts*))

(setq *autolisp-reference-parts*
  (cons
    '(("gcd" .
          ((name . "gcd")
           (title . "gcd (AutoLISP)")
           (summary . "Returns the greatest common denominator of two integers")
           (source-kind . "AutoLISP")
           (alphabetic-group . "G")
           (feature-groups . ("Arithmetic"))
           (supported-platforms . "Windows and Mac OS")
           (signature . "(gcd int1 int2)")
           (arguments . (("int1" . "Type: Integer\nAn integer; must be greater than 0.")
                           ("int2" . "Type: Integer\nAn integer; must be greater than 0.")))
           (return-values . "Type: Integer\nAn integer representing the greatest common denominator between int1 and int2.")
           (release-information . nil)
           (history . nil)
           (examples . "(gcd 81 57)\n3\n\n(gcd 12 20)\n4")
           (url . "https://help.autodesk.com/cloudhelp/2023/ENU/AutoCAD-AutoLISP-Reference/files/GUID-3F748964-B6D7-4136-92D5-81A7DD02ED4A.htm")
           (guid . "GUID-3F748964-B6D7-4136-92D5-81A7DD02ED4A"))))
    *autolisp-reference-parts*))

(setq *autolisp-reference-parts*
  (cons
    '(("get_attr" .
          ((name . "get_attr")
           (title . "get_attr (AutoLISP/DCL)")
           (summary . "Retrieves the DCL value of a dialog box attribute")
           (source-kind . "AutoLISP/DCL")
           (alphabetic-group . "G")
           (feature-groups . ("Tile- and Attribute-Handling Functions Reference (AutoLISP/DCL)"))
           (supported-platforms . "Windows and Mac OS")
           (signature . "(get_attr key attribute)")
           (arguments . (("key" . "Type: String\nValue that specifies a tile. This argument is case-sensitive.")
                           ("attribute" . "Type: String\nName of the attribute as it appears in the tile's DCL description.")))
           (return-values . "Type: String\nA value containing the attribute's initial value as specified in its DCL description.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-AB9100B0-F19E-4C29-B82A-28E8A607BF4E.htm")
           (guid . "GUID-AB9100B0-F19E-4C29-B82A-28E8A607BF4E"))))
    *autolisp-reference-parts*))

(setq *autolisp-reference-parts*
  (cons
    '(("get_tile" .
          ((name . "get_tile")
           (title . "get_tile (AutoLISP/DCL)")
           (summary . "Retrieves the current runtime value of a dialog box tile")
           (source-kind . "AutoLISP/DCL")
           (alphabetic-group . "G")
           (feature-groups . ("Tile- and Attribute-Handling Functions Reference (AutoLISP/DCL)"))
           (supported-platforms . "Windows and Mac OS")
           (signature . "(get_tile key)")
           (arguments . (("key" . "Type: String\nValue that specifies a tile. This argument is case-sensitive.")))
           (return-values . "Type: String\nA textual value containing the tile's value.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-3BD2F6DF-DCD5-4A00-9BDF-E2C7C7C286F8.htm")
           (guid . "GUID-3BD2F6DF-DCD5-4A00-9BDF-E2C7C7C286F8"))))
    *autolisp-reference-parts*))

(setq *autolisp-reference-parts*
  (cons
    '(("getangle" .
          ((name . "getangle")
           (title . "getangle (AutoLISP)")
           (summary . "Pauses for user input of an angle, and returns that angle in radians")
           (source-kind . "AutoLISP")
           (alphabetic-group . "G")
           (feature-groups . ("User Input"))
           (supported-platforms . "Windows and Mac OS")
           (signature . "(getangle [pt] [msg])")
           (arguments . (("pt" . "Type: List\nA 2D base point in the current UCS.\nThe pt argument, if specified, is assumed to be the first of two points, so the user can show AutoLISP the angle by pointing to one other point. You can supply a 3D base point, but the angle is always measured in the current construction plane.")
                           ("msg" . "Type: String\nMessage to be displayed to prompt the user.")))
           (return-values . nil)
           (release-information . nil)
           (history . nil)
           (examples . "The following code examples show how different arguments can be used with getangle:\n\n(setq ang (getangle))\n(setq ang (getangle '(1.0 3.5)))\n(setq ang (getangle \"Which way? \"))\n(setq ang (getangle '(1.0 3.5) \"Which way? \"))")
           (url . "https://help.autodesk.com/cloudhelp/2023/ENU/AutoCAD-AutoLISP-Reference/files/GUID-947F34FA-5E58-4C7C-A169-556D4B8E2208.htm")
           (guid . "GUID-947F34FA-5E58-4C7C-A169-556D4B8E2208"))))
    *autolisp-reference-parts*))

(setq *autolisp-reference-parts*
  (cons
    '(("getcfg" .
          ((name . "getcfg")
           (title . "getcfg (AutoLISP)")
           (summary . "Obsolete. Retrieves application data from the AppData section of the acad20xx.cfg file")
           (source-kind . "AutoLISP")
           (alphabetic-group . "G")
           (feature-groups . ("Query and Command"))
           (supported-platforms . "Windows and Mac OS")
           (signature . "(getcfg cfgname)\n\n\"AppData/application_name/section_name/.../param_name\"")
           (arguments . (("cfgname" . "Type: String\nSection name and parameter value to retrieve (maximum length of 496 characters).")))
           (return-values . "Type: String or nil\nApplication data, if successful. If cfgname is not valid, getcfg returns nil.")
           (release-information . nil)
           (history . nil)
           (examples . "Assuming the WallThk parameter in the AppData/ArchStuff section has a value of 8, the following command retrieves that value:\n\n(getcfg \"AppData/ArchStuff/WallThk\")\n\"8\"")
           (url . "https://help.autodesk.com/cloudhelp/2023/ENU/AutoCAD-AutoLISP-Reference/files/GUID-D8D46A8C-82DF-4193-A1B7-3DC3CAC70650.htm")
           (guid . "GUID-D8D46A8C-82DF-4193-A1B7-3DC3CAC70650"))))
    *autolisp-reference-parts*))

(setq *autolisp-reference-parts*
  (cons
    '(("getcname" .
          ((name . "getcname")
           (title . "getcname (AutoLISP)")
           (summary . "Retrieves the localized or English name of an AutoCAD command")
           (source-kind . "AutoLISP")
           (alphabetic-group . "G")
           (feature-groups . ("Query and Command"))
           (supported-platforms . "Windows and Mac OS")
           (signature . "(getcname cname)")
           (arguments . (("cname" . "Type: String\nThe localized or underscored English command name; must be 64 characters or less in length.")))
           (return-values . "If cname is not preceded by an underscore (assumed to be the localized command name), getcname returns the underscored English command name. If cname is preceded by an underscore, getcname returns the localized command name. This function returns nil if cname is not a valid command name.")
           (release-information . nil)
           (history . nil)
           (examples . "In a French version of AutoCAD, the following is True.\n\n(getcname \"ETIRER\")\n\"_STRETCH\"\n\n(getcname \"_STRETCH\")\n\"ETIRER\"")
           (url . "https://help.autodesk.com/cloudhelp/2023/ENU/AutoCAD-AutoLISP-Reference/files/GUID-1DCDFFA6-0372-479D-B00F-D165EC5B8A2C.htm")
           (guid . "GUID-1DCDFFA6-0372-479D-B00F-D165EC5B8A2C"))))
    *autolisp-reference-parts*))

(setq *autolisp-reference-parts*
  (cons
    '(("getcorner" .
          ((name . "getcorner")
           (title . "getcorner (AutoLISP)")
           (summary . "Pauses for user input of a rectangle's second corner")
           (source-kind . "AutoLISP")
           (alphabetic-group . "G")
           (feature-groups . ("User Input"))
           (supported-platforms . "Windows and Mac OS")
           (signature . "(getcorner pt [msg])")
           (arguments . (("pt" . "Type: List\nA point to be used as the base point.")
                           ("msg" . "Type: String\nMessage to be displayed to prompt the user.")))
           (return-values . "Type: List or nil\nThe getcorner function returns a point in the current UCS, similar to getpoint. If the user supplies a 3D point, its Z coordinate is ignored. The current elevation is used as the Z coordinate.")
           (release-information . nil)
           (history . nil)
           (examples . "(getcorner '(7.64935 6.02964 0.0))\n(17.2066 1.47628 0.0)\n\n(getcorner '(7.64935 6.02964 0.0) \"\\nPick a corner\")\nPick a corner(15.9584 2.40119 0.0)")
           (url . "https://help.autodesk.com/cloudhelp/2023/ENU/AutoCAD-AutoLISP-Reference/files/GUID-21BE8290-7F11-400B-AC39-62A110F07545.htm")
           (guid . "GUID-21BE8290-7F11-400B-AC39-62A110F07545"))))
    *autolisp-reference-parts*))

(setq *autolisp-reference-parts*
  (cons
    '(("getdist" .
          ((name . "getdist")
           (title . "getdist (AutoLISP)")
           (summary . "Pauses for user input of a distance")
           (source-kind . "AutoLISP")
           (alphabetic-group . "G")
           (feature-groups . ("User Input"))
           (supported-platforms . "Windows and Mac OS")
           (signature . "(getdist [pt] [msg])")
           (arguments . (("pt" . "Type: List\nA 2D or 3D point to be used as the base point in the current UCS. If pt is provided, the user is prompted for the second point.")
                           ("msg" . "Type: String\nMessage to be displayed to prompt the user. If no string is supplied, AutoCAD does not display a message.")))
           (return-values . "Type: Real or nil\nA numeric value. If a 3D point is provided, the returned value is a 3D distance. However, setting the 64 bit of the initget function instructs getdist to ignore the Z component of 3D points and to return a 2D distance.")
           (release-information . nil)
           (history . nil)
           (examples . "(setq dist (getdist))\n(setq dist (getdist '(1.0 3.5)))\n(setq dist (getdist \"How far \"))\n(setq dist (getdist '(1.0 3.5) \"How far? \"))")
           (url . "https://help.autodesk.com/cloudhelp/2023/ENU/AutoCAD-AutoLISP-Reference/files/GUID-7D381B2A-79AA-4133-9C96-3DA63F8D8632.htm")
           (guid . "GUID-7D381B2A-79AA-4133-9C96-3DA63F8D8632"))))
    *autolisp-reference-parts*))

(setq *autolisp-reference-parts*
  (cons
    '(("getenv" .
          ((name . "getenv")
           (title . "getenv (AutoLISP)")
           (summary . "Returns the string value assigned to a system environment variable")
           (source-kind . "AutoLISP")
           (alphabetic-group . "G")
           (feature-groups . ("Query and Command"))
           (supported-platforms . "Windows and Mac OS")
           (signature . "(getenv variable-name)")
           (arguments . (("variable-name" . "Type: String\nA string specifying the name of the variable to be read. Environment variable names must be spelled and cased exactly as they are stored in the system registry.")))
           (return-values . "Type: String or nil\nA string representing the value assigned to the specified system variable. If the variable does not exist, getenv returns nil.")
           (release-information . nil)
           (history . nil)
           (examples . "Assume the system environment variable ACAD is set to /acad/support and there is no variable named NOSUCH.\n\n(getenv \"ACAD\")\n\"/acad/support\"\n\n(getenv \"NOSUCH\")\nnil\n\nAssume that the MaxArray environment variable is set to 10000:\n\n(getenv \"MaxArray\")\n\"10000\"")
           (url . "https://help.autodesk.com/cloudhelp/2023/ENU/AutoCAD-AutoLISP-Reference/files/GUID-0796D4FE-C07B-4DB6-9C01-9D772CAFA2C0.htm")
           (guid . "GUID-0796D4FE-C07B-4DB6-9C01-9D772CAFA2C0"))))
    *autolisp-reference-parts*))

(setq *autolisp-reference-entry* nil)

(setq *autolisp-reference-value* "GUID-AD65DF88-5218-4655-B877-B4D33B9FB6D1")

(setq *autolisp-reference-entry* (cons (cons 'guid *autolisp-reference-value*) *autolisp-reference-entry*))

(setq *autolisp-reference-value* "https://help.autodesk.com/cloudhelp/2023/ENU/AutoCAD-AutoLISP-Reference/files/GUID-AD65DF88-5218-4655-B877-B4D33B9FB6D1.htm")

(setq *autolisp-reference-entry* (cons (cons 'url *autolisp-reference-value*) *autolisp-reference-entry*))

(setq *autolisp-reference-value* "The following call to getfiled displays the Select a Lisp File dialog box:\n\nWindows\n\n(getfiled \"Select a Lisp File\" \"c:/program files/<AutoCAD installation directory>/support/\" \"lsp\" 8)\n\nMac OS\n\n(getfiled \"Select a Lisp File\" \"/Applications/Autodesk/<AutoCAD installation directory>/<product name>.app/\" \"lsp\" 8)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String or nil\nIf the dialog box obtains a file name from the user, getfiled returns a string that specifies the file name; otherwise, it returns nil.")

(setq *autolisp-reference-entry* (cons (cons 'return-values *autolisp-reference-value*) *autolisp-reference-entry*))

(setq *autolisp-reference-value* nil)

(setq *autolisp-reference-string* "Type: Integer\nAn integer value (a bit-coded field) that controls the behavior of the dialog box. To set more than one condition at a time, add the values together to create a flags value between 0 and 15. The following flags arguments are recognized by getfiled:\n1 (bit 0) -- Prompt for the name of a new file to create. Do not set this bit when you prompt for the name of an existing file to open. In the latter case, if the user enters the name of a file that doesn't exist, the dialog box displays an error message at the bottom of the box.\nIf this bit is set and the user chooses a file that already exists, AutoCAD displays an alert box and offers the choice of proceeding with or canceling the operation.\n4 (bit 2) -- Let the user enter an arbitrary file name extension, or no extension at all.\nIf this bit is not set, getfiled accepts only the extension specified in the ext argument and ")

(setq *autolisp-reference-string* (strcat *autolisp-reference-string* "appends this extension to the file name if the user doesn't enter it in the File text box.\n8 (bit 3) -- If this bit is set and bit 0 is not set, getfiled performs a library search for the file name entered. If it finds the file and its directory in the library search path, it strips the path and returns only the file name. (It does not strip the path name if it finds that a file of the same name is in a different directory.)\nIf this bit is not set, getfiled returns the entire file name, including the path name.\nSet this bit if you use the dialog box to open an existing file whose name you want to save in the drawing (or other database).\n16 (bit 4) -- If this bit is set, or if the default argument ends with a path delimiter, the argument is interpreted as a path name only. The getfiled function assumes that there is no default file name. It displays the path in the Look in: line and l"))

(setq *autolisp-reference-string* (strcat *autolisp-reference-string* "eaves the File name box blank.\n32 (bit 5) -- If this bit is set and bit 0 is set (indicating that a new file is being specified), users will not be warned if they are about to overwrite an existing file. The alert box to warn users that a file of the same name already exists will not be displayed; the old file will just be replaced.\n64 (bit 6) -- Do not transfer the remote file if the user specifies a URL.\n128 (bit 7) -- Do not allow URLs at all."))

(setq *autolisp-reference-value* (cons (cons "flags" *autolisp-reference-string*) *autolisp-reference-value*))

(setq *autolisp-reference-string* "Type: String\nThe default file name extension. If ext is passed as a null string (\"\"), it defaults to * (all file types).\nIf the file type dwg is included in the ext argument, the getfiled function displays an image preview in the dialog box.")

(setq *autolisp-reference-value* (cons (cons "ext" *autolisp-reference-string*) *autolisp-reference-value*))

(setq *autolisp-reference-string* "Type: String\nA default file name to use; can be a null string (\"\").")

(setq *autolisp-reference-value* (cons (cons "default" *autolisp-reference-string*) *autolisp-reference-value*))

(setq *autolisp-reference-string* "Type: String\nThe dialog box label.")

(setq *autolisp-reference-value* (cons (cons "title" *autolisp-reference-string*) *autolisp-reference-value*))

(setq *autolisp-reference-entry* (cons (cons 'arguments *autolisp-reference-value*) *autolisp-reference-entry*))

(setq *autolisp-reference-value* "(getfiled title default ext flags)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("User Input"))

(setq *autolisp-reference-entry* (cons (cons 'feature-groups *autolisp-reference-value*) *autolisp-reference-entry*))

(setq *autolisp-reference-value* "G")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Prompts the user for a file name with the standard AutoCAD file dialog box, and returns that file name")

(setq *autolisp-reference-entry* (cons (cons 'summary *autolisp-reference-value*) *autolisp-reference-entry*))

(setq *autolisp-reference-value* "getfiled (AutoLISP)")

(setq *autolisp-reference-entry* (cons (cons 'title *autolisp-reference-value*) *autolisp-reference-entry*))

(setq *autolisp-reference-value* "getfiled")

(setq *autolisp-reference-entry* (cons (cons 'name *autolisp-reference-value*) *autolisp-reference-entry*))

(setq *autolisp-reference-parts* (cons (list (cons "getfiled" *autolisp-reference-entry*)) *autolisp-reference-parts*))

(setq *autolisp-reference-parts*
  (cons
    '(("getint" .
          ((name . "getint")
           (title . "getint (AutoLISP)")
           (summary . "Pauses for user input of an integer, and returns that integer")
           (source-kind . "AutoLISP")
           (alphabetic-group . "G")
           (feature-groups . ("User Input"))
           (supported-platforms . "Windows and Mac OS")
           (signature . "(getint [msg])")
           (arguments . (("msg" . "Type: String\nMessage to be displayed to prompt the user; if omitted, no message is displayed.")))
           (return-values . "Type: Integer or nil\nThe integer specified by the user; otherwise nil, if the user presses Enter without entering an integer.")
           (release-information . nil)
           (history . nil)
           (examples . "(setq num (getint))\n15\n15\n\n(setq num (getint \"Enter a number:\"))\nEnter a number: 25\n25\n\n(setq num (getint))\n15.0\nRequires an integer value.\n15\n15")
           (url . "https://help.autodesk.com/cloudhelp/2023/ENU/AutoCAD-AutoLISP-Reference/files/GUID-18D6FF0F-B1DF-447D-BC6C-A46C933EF78B.htm")
           (guid . "GUID-18D6FF0F-B1DF-447D-BC6C-A46C933EF78B"))))
    *autolisp-reference-parts*))

(setq *autolisp-reference-entry* nil)

(setq *autolisp-reference-value* "GUID-9F940144-0D7B-4DA1-BF50-BBF8FB8DFF21")

(setq *autolisp-reference-entry* (cons (cons 'guid *autolisp-reference-value*) *autolisp-reference-entry*))

(setq *autolisp-reference-value* "https://help.autodesk.com/cloudhelp/2023/ENU/AutoCAD-AutoLISP-Reference/files/GUID-9F940144-0D7B-4DA1-BF50-BBF8FB8DFF21.htm")

(setq *autolisp-reference-entry* (cons (cons 'url *autolisp-reference-value*) *autolisp-reference-entry*))

(setq *autolisp-reference-value* "The following example shows an initial call to initget that sets up a list of keywords (Yes and No) and disallows null input (bits value equal to 1) to the getkword call that follows:\n\n(initget 1 \"Yes No\")\nnil\n\n(setq x (getkword \"Are you sure? (Yes or No) \"))\nAre you sure? (Yes or No) yes\n\"Yes\"\n\nThe following sequence illustrates what happens if the user enters invalid data in response to getkword:\n\n(initget 1 \"Yes No\")\nnil\n\n(setq x (getkword \"Are you sure? (Yes or No) \"))\nAre you sure? (Yes or No) Maybe\nInvalid option keyword.\nAre you sure? (Yes or No) yes\n\"Yes\"\n\nThe user's response was not one of the keywords defined by the preceding initget, so getkword issued an error message and then prompted the user again with the string supplied in the msg argument.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String or nil\nA string representing the keyword entered by the user; otherwise nil, if the user presses Enter without typing a keyword. The function also returns nil if it was not preceded by a call to initget to establish one or more keywords.\nIf the user enters a value that is not a valid keyword, getkword displays a warning message and prompts the user to try again.")

(setq *autolisp-reference-entry* (cons (cons 'return-values *autolisp-reference-value*) *autolisp-reference-entry*))

(setq *autolisp-reference-value* nil)

(setq *autolisp-reference-string* "Type: String\nMessage to be displayed to prompt the user; if omitted, getkword does not display a prompting message.")

(setq *autolisp-reference-value* (cons (cons "msg" *autolisp-reference-string*) *autolisp-reference-value*))

(setq *autolisp-reference-entry* (cons (cons 'arguments *autolisp-reference-value*) *autolisp-reference-entry*))

(setq *autolisp-reference-value* "(getkword [msg])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("User Input"))

(setq *autolisp-reference-entry* (cons (cons 'feature-groups *autolisp-reference-value*) *autolisp-reference-entry*))

(setq *autolisp-reference-value* "G")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Pauses for user input of a keyword, and returns that keyword")

(setq *autolisp-reference-entry* (cons (cons 'summary *autolisp-reference-value*) *autolisp-reference-entry*))

(setq *autolisp-reference-value* "getkword (AutoLISP)")

(setq *autolisp-reference-entry* (cons (cons 'title *autolisp-reference-value*) *autolisp-reference-entry*))

(setq *autolisp-reference-value* "getkword")

(setq *autolisp-reference-entry* (cons (cons 'name *autolisp-reference-value*) *autolisp-reference-entry*))

(setq *autolisp-reference-parts* (cons (list (cons "getkword" *autolisp-reference-entry*)) *autolisp-reference-parts*))

(setq *autolisp-reference-parts*
  (cons
    '(("getorient" .
          ((name . "getorient")
           (title . "getorient (AutoLISP)")
           (summary . "Pauses for user input of an angle, and returns that angle in radians")
           (source-kind . "AutoLISP")
           (alphabetic-group . "G")
           (feature-groups . ("User Input"))
           (supported-platforms . "Windows and Mac OS")
           (signature . "(getorient [pt] [msg])")
           (arguments . (("pt" . "Type: List\nA 2D base point in the current UCS.\nThe pt argument, if specified, is assumed to be the first of two points, so that the user can show AutoLISP the angle by pointing to one other point. You can supply a 3D base point, but the angle is always measured in the current construction plane.")
                           ("msg" . "Type: String\nMessage to be displayed to prompt the user.")))
           (return-values . "Type: Real or nil\nThe angle specified by the user, in radians, with respect to the current construction plane.")
           (release-information . nil)
           (history . nil)
           (examples . "(setq pt1 (getpoint \"Pick point: \"))\n(4.55028 5.84722 0.0)\n\n(getorient pt1 \"Pick point: \")\n5.61582")
           (url . "https://help.autodesk.com/cloudhelp/2023/ENU/AutoCAD-AutoLISP-Reference/files/GUID-4F8606DD-6453-4D01-84C6-EC8EEBBE2D1A.htm")
           (guid . "GUID-4F8606DD-6453-4D01-84C6-EC8EEBBE2D1A"))))
    *autolisp-reference-parts*))

(setq *autolisp-reference-parts*
  (cons
    '(("getpoint" .
          ((name . "getpoint")
           (title . "getpoint (AutoLISP)")
           (summary . "Pauses for user input of a point, and returns that point")
           (source-kind . "AutoLISP")
           (alphabetic-group . "G")
           (feature-groups . ("User Input"))
           (supported-platforms . "Windows and Mac OS")
           (signature . "(getpoint [pt] [msg])")
           (arguments . (("pt" . "Type: List\nA 2D or 3D base point in the current UCS.\nNote: getpoint will accept a single integer or real number as the pt argument, and use the AutoCAD direct distance entry mechanism to determine a point. This mechanism uses the value of the AutoCAD LASTPOINT system variable as the starting point, the pt input as the distance, and the current cursor location as the direction from LASTPOINT. The result is a point that is the specified number of units away from LASTPOINT in the direction of the current cursor location.")
                           ("msg" . "Type: String\nMessage to be displayed to prompt the user.")))
           (return-values . "Type: List or nil\nA 3D point, expressed in terms of the current UCS.")
           (release-information . nil)
           (history . nil)
           (examples . "(setq p (getpoint))\n(setq p (getpoint \"Where? \"))\n(setq p (getpoint '(1.5 2.0) \"Second point: \"))")
           (url . "https://help.autodesk.com/cloudhelp/2023/ENU/AutoCAD-AutoLISP-Reference/files/GUID-445F32F0-8A9D-4E1D-976F-DE87CC5267D0.htm")
           (guid . "GUID-445F32F0-8A9D-4E1D-976F-DE87CC5267D0"))))
    *autolisp-reference-parts*))

(setq *autolisp-reference-entry* nil)

(setq *autolisp-reference-value* "GUID-8E5913FC-09ED-4C70-AFB7-2431C062E899")

(setq *autolisp-reference-entry* (cons (cons 'guid *autolisp-reference-value*) *autolisp-reference-entry*))

(setq *autolisp-reference-value* "https://help.autodesk.com/cloudhelp/2023/ENU/AutoCAD-AutoLISP-Reference/files/GUID-8E5913FC-09ED-4C70-AFB7-2431C062E899.htm")

(setq *autolisp-reference-entry* (cons (cons 'url *autolisp-reference-value*) *autolisp-reference-entry*))

(setq *autolisp-reference-value* "The following example demonstrates how to get the current radius value of a circle.\n\n(command \"_circle\" \"2,2\" 2)\nnil\n\n(getpropertyvalue (entlast) \"radius\")\n2.0")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, List, T, or nil\nThe value of the entity’s property.")

(setq *autolisp-reference-entry* (cons (cons 'return-values *autolisp-reference-value*) *autolisp-reference-entry*))

(setq *autolisp-reference-value* nil)

(setq *autolisp-reference-string* "Type: String\nThe name of the property within the collection being queried.")

(setq *autolisp-reference-value* (cons (cons "name" *autolisp-reference-string*) *autolisp-reference-value*))

(setq *autolisp-reference-string* "Type: Integer\nThe collection index being queried.")

(setq *autolisp-reference-value* (cons (cons "index" *autolisp-reference-string*) *autolisp-reference-value*))

(setq *autolisp-reference-string* "Type: String\nIf the object is a collection object, the Collection name is passed here.")

(setq *autolisp-reference-value* (cons (cons "collectionName" *autolisp-reference-string*) *autolisp-reference-value*))

(setq *autolisp-reference-string* "Type: String\nName of the property being queried. For a list of all the valid property names of a given object, use dumpallproperties.")

(setq *autolisp-reference-value* (cons (cons "propertyname" *autolisp-reference-string*) *autolisp-reference-value*))

(setq *autolisp-reference-string* "Type: Ename (entity name)\nName of the entity being queried. The ename can refer to either a graphical or a nongraphical entity.")

(setq *autolisp-reference-value* (cons (cons "ename" *autolisp-reference-string*) *autolisp-reference-value*))

(setq *autolisp-reference-entry* (cons (cons 'arguments *autolisp-reference-value*) *autolisp-reference-entry*))

(setq *autolisp-reference-value* "(getpropertyvalue ename propertyname [or collectionName index name])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Object-Handling"))

(setq *autolisp-reference-entry* (cons (cons 'feature-groups *autolisp-reference-value*) *autolisp-reference-entry*))

(setq *autolisp-reference-value* "G")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns the current value of an entity’s property")

(setq *autolisp-reference-entry* (cons (cons 'summary *autolisp-reference-value*) *autolisp-reference-entry*))

(setq *autolisp-reference-value* "getpropertyvalue (AutoLISP)")

(setq *autolisp-reference-entry* (cons (cons 'title *autolisp-reference-value*) *autolisp-reference-entry*))

(setq *autolisp-reference-value* "getpropertyvalue")

(setq *autolisp-reference-entry* (cons (cons 'name *autolisp-reference-value*) *autolisp-reference-entry*))

(setq *autolisp-reference-parts* (cons (list (cons "getpropertyvalue" *autolisp-reference-entry*)) *autolisp-reference-parts*))

(setq *autolisp-reference-parts*
  (cons
    '(("getreal" .
          ((name . "getreal")
           (title . "getreal (AutoLISP)")
           (summary . "Pauses for user input of a real number, and returns that real number")
           (source-kind . "AutoLISP")
           (alphabetic-group . "G")
           (feature-groups . ("User Input"))
           (supported-platforms . "Windows and Mac OS")
           (signature . "(getreal [msg])")
           (arguments . (("msg" . "Type: String\nMessage to be displayed to prompt the user.")))
           (return-values . "Type: Real or nil\nThe number entered by the user and expressed as a real.")
           (release-information . nil)
           (history . nil)
           (examples . "(setq val (getreal))\n(setq val (getreal \"Scale factor: \"))")
           (url . "https://help.autodesk.com/cloudhelp/2023/ENU/AutoCAD-AutoLISP-Reference/files/GUID-503BBE86-9B22-456A-8883-1B5F5832B7E0.htm")
           (guid . "GUID-503BBE86-9B22-456A-8883-1B5F5832B7E0"))))
    *autolisp-reference-parts*))

(setq *autolisp-reference-entry* nil)

(setq *autolisp-reference-value* "GUID-B139EFBD-74B7-4276-B422-D2186F7D8D0A")

(setq *autolisp-reference-entry* (cons (cons 'guid *autolisp-reference-value*) *autolisp-reference-entry*))

(setq *autolisp-reference-value* "https://help.autodesk.com/cloudhelp/2023/ENU/AutoCAD-AutoLISP-Reference/files/GUID-B139EFBD-74B7-4276-B422-D2186F7D8D0A.htm")

(setq *autolisp-reference-entry* (cons (cons 'url *autolisp-reference-value*) *autolisp-reference-entry*))

(setq *autolisp-reference-value* "(setq s (getstring \"What's your first name? \"))\nWhat's your first name? Gary\n\"Gary\"\n\n(setq s (getstring T \"What's your full name? \"))\nWhat's your full name? Gary Indiana Jones\n\"Gary Indiana Jones\"\n\n(setq s (getstring T \"Enter filename: \"))\nEnter filename: c:\\my documents\\vlisp\\secrets\n\"c:\\\\my documents\\\\vlisp\\\\secrets\"")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String\nThe string entered by the user; otherwise nil, if the user pressed Enter without typing a string.\nIf the string is longer than 132 characters, getstring returns only the first 132 characters of the string. If the input string contains the backslash character (\\), getstring converts it to two backslash characters (\\\\). This allows you to use returned values containing file name paths in other functions.")

(setq *autolisp-reference-entry* (cons (cons 'return-values *autolisp-reference-value*) *autolisp-reference-entry*))

(setq *autolisp-reference-value* nil)

(setq *autolisp-reference-string* "Type: String\nMessage to be displayed to prompt the user.")

(setq *autolisp-reference-value* (cons (cons "msg" *autolisp-reference-string*) *autolisp-reference-value*))

(setq *autolisp-reference-string* "Type: T or nil\nIf supplied and not nil, this argument indicates that users can include blanks in their input string (and must terminate the string by pressing Enter). Otherwise, the input string is terminated by entering a space or pressing Enter.")

(setq *autolisp-reference-value* (cons (cons "cr" *autolisp-reference-string*) *autolisp-reference-value*))

(setq *autolisp-reference-entry* (cons (cons 'arguments *autolisp-reference-value*) *autolisp-reference-entry*))

(setq *autolisp-reference-value* "(getstring [cr] [msg])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("User Input"))

(setq *autolisp-reference-entry* (cons (cons 'feature-groups *autolisp-reference-value*) *autolisp-reference-entry*))

(setq *autolisp-reference-value* "G")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Pauses for user input of a string, and returns that string")

(setq *autolisp-reference-entry* (cons (cons 'summary *autolisp-reference-value*) *autolisp-reference-entry*))

(setq *autolisp-reference-value* "getstring (AutoLISP)")

(setq *autolisp-reference-entry* (cons (cons 'title *autolisp-reference-value*) *autolisp-reference-entry*))

(setq *autolisp-reference-value* "getstring")

(setq *autolisp-reference-entry* (cons (cons 'name *autolisp-reference-value*) *autolisp-reference-entry*))

(setq *autolisp-reference-parts* (cons (list (cons "getstring" *autolisp-reference-entry*)) *autolisp-reference-parts*))

(setq *autolisp-reference-parts*
  (cons
    '(("getvar" .
          ((name . "getvar")
           (title . "getvar (AutoLISP)")
           (summary . "Retrieves the value of an AutoCAD system variable")
           (source-kind . "AutoLISP")
           (alphabetic-group . "G")
           (feature-groups . ("Query and Command"))
           (supported-platforms . "Windows and Mac OS")
           (signature . "(getvar varname)")
           (arguments . (("varname" . "Type: String\nNames of a system variable.\nSee the product's Help system for a list of current AutoCAD system variables.")))
           (return-values . "Type: Integer, Real, String, List, or nil\nThe value of the system variable; otherwise nil, if varname is not a valid system variable.")
           (release-information . nil)
           (history . nil)
           (examples . "Get the current value of the fillet radius:\n\n(getvar 'FILLETRAD)\n0.25")
           (url . "https://help.autodesk.com/cloudhelp/2023/ENU/AutoCAD-AutoLISP-Reference/files/GUID-9C56BEA8-D473-4305-9E17-BEF7630C334D.htm")
           (guid . "GUID-9C56BEA8-D473-4305-9E17-BEF7630C334D"))))
    *autolisp-reference-parts*))

(setq *autolisp-reference-parts*
  (cons
    '(("graphscr" .
          ((name . "graphscr")
           (title . "graphscr (AutoLISP)")
           (summary . "Displays the AutoCAD graphics screen")
           (source-kind . "AutoLISP")
           (alphabetic-group . "G")
           (feature-groups . ("Display Control"))
           (supported-platforms . "Windows and Mac OS")
           (signature . "(graphscr)")
           (arguments . nil)
           (return-values . "Type: nil\nAlways returns nil.")
           (release-information . nil)
           (history . nil)
           (examples . "N/A")
           (url . "https://help.autodesk.com/cloudhelp/2023/ENU/AutoCAD-AutoLISP-Reference/files/GUID-FB9ABA5D-6DDA-4085-9E9F-18038EC31107.htm")
           (guid . "GUID-FB9ABA5D-6DDA-4085-9E9F-18038EC31107"))))
    *autolisp-reference-parts*))

(setq *autolisp-reference-parts*
  (cons
    '(("grclear" .
          ((name . "grclear")
           (title . "grclear (AutoLISP)")
           (summary . "Clears the current viewport (obsolete)")
           (source-kind . "AutoLISP")
           (alphabetic-group . "G")
           (feature-groups . nil)
           (supported-platforms . "Windows and Mac OS")
           (signature . "(grclear)")
           (arguments . nil)
           (return-values . "Type: nil\nAlways returns nil.")
           (release-information . nil)
           (history . nil)
           (examples . "N/A")
           (url . "https://help.autodesk.com/cloudhelp/2023/ENU/AutoCAD-AutoLISP-Reference/files/GUID-66CBF3AE-39E8-4412-AF3E-1A6D56951B73.htm")
           (guid . "GUID-66CBF3AE-39E8-4412-AF3E-1A6D56951B73"))))
    *autolisp-reference-parts*))

(setq *autolisp-reference-parts*
  (cons
    '(("grdraw" .
          ((name . "grdraw")
           (title . "grdraw (AutoLISP)")
           (summary . "Draws a vector between two points, in the current viewport")
           (source-kind . "AutoLISP")
           (alphabetic-group . "G")
           (feature-groups . ("Display Control"))
           (supported-platforms . "Windows and Mac OS")
           (signature . "(grdraw from to color [highlight])")
           (arguments . (("from" . "Type: List\n2D or 3D points (lists of two or three reals) specifying one endpoint of the vector in terms of the current UCS. AutoCAD clips the vector to fit the screen.")
                           ("to" . "Type: List\n2D or 3D points (lists of two or three reals) specifying the other endpoint of the vector in terms of the current UCS. AutoCAD clips the vector to fit the screen.")
                           ("color" . "Type: Integer\nColor used to draw the vector. A -1 signifies XOR ink, which complements anything it draws over and which erases itself when overdrawn.")
                           ("highlight" . "Type: Integer\nOther than zero, indicates that the vector is to be drawn using the default highlighting method of the display device (usually dashed).\nIf highlight is omitted or is zero, grdraw uses the normal display mode.")))
           (return-values . "Type: nil\nAlways returns nil.")
           (release-information . nil)
           (history . nil)
           (examples . "N/A")
           (url . "https://help.autodesk.com/cloudhelp/2023/ENU/AutoCAD-AutoLISP-Reference/files/GUID-C00544A7-AF63-403E-98EB-205248EB4F54.htm")
           (guid . "GUID-C00544A7-AF63-403E-98EB-205248EB4F54"))))
    *autolisp-reference-parts*))

(setq *autolisp-reference-entry* nil)

(setq *autolisp-reference-value* "GUID-2484FFE3-95B3-4C2B-AF79-BE7772B07419")

(setq *autolisp-reference-entry* (cons (cons 'guid *autolisp-reference-value*) *autolisp-reference-entry*))

(setq *autolisp-reference-value* "https://help.autodesk.com/cloudhelp/2023/ENU/AutoCAD-AutoLISP-Reference/files/GUID-2484FFE3-95B3-4C2B-AF79-BE7772B07419.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nThe grread function returns a list whose first element is a code specifying the type of input. The second element of the list is either an integer or a point, depending on the type of input. The return values are listed in the following table:")

(setq *autolisp-reference-entry* (cons (cons 'return-values *autolisp-reference-value*) *autolisp-reference-entry*))

(setq *autolisp-reference-value* nil)

(setq *autolisp-reference-string* "An integer indicating the type of cursor to be displayed. The allkeys value for bit 2 must be set for the curtype values to take effect. The curtype argument affects only the cursor type during the current grread function call. You can specify one of the following values for curtype:\n0 -- Display the normal crosshairs.\n1 -- Do not display a cursor (no crosshairs).\n2 -- Display the object-selection “target” cursor.")

(setq *autolisp-reference-value* (cons (cons "curtype" *autolisp-reference-string*) *autolisp-reference-value*))

(setq *autolisp-reference-string* "Type: Integer\nCode that tells grread what functions to perform. The allkeys bit code values can be added together for combined functionality. The following values can be specified:\n1(bit 0) -- Return drag mode coordinates. If this bit is set and the user moves the pointing device instead of selecting a button or pressing a key, grread returns a list where the first member is a type 5 and the second member is the (X,Y) coordinates of the current pointing device (mouse or digitizer) location. This is how AutoCAD implements dragging.\n2 (bit 1) -- Return all key values, including function and cursor key codes, and do not move the cursor when the user presses a cursor key.\n4 (bit 2) -- Use the value passed in the curtype argument to control the cursor display.\n8 (bit 3) -- Do not display the error: console break message when the user presses Esc.")

(setq *autolisp-reference-value* (cons (cons "allkeys" *autolisp-reference-string*) *autolisp-reference-value*))

(setq *autolisp-reference-string* "Type: T or nil\nIf supplied and not nil, this argument enables the return of coordinates from a pointing device as it is moved.")

(setq *autolisp-reference-value* (cons (cons "track" *autolisp-reference-string*) *autolisp-reference-value*))

(setq *autolisp-reference-entry* (cons (cons 'arguments *autolisp-reference-value*) *autolisp-reference-entry*))

(setq *autolisp-reference-value* "(grread [track] [allkeys [curtype]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Device Access"))

(setq *autolisp-reference-entry* (cons (cons 'feature-groups *autolisp-reference-value*) *autolisp-reference-entry*))

(setq *autolisp-reference-value* "G")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Reads values from any of the AutoCAD input devices")

(setq *autolisp-reference-entry* (cons (cons 'summary *autolisp-reference-value*) *autolisp-reference-entry*))

(setq *autolisp-reference-value* "grread (AutoLISP)")

(setq *autolisp-reference-entry* (cons (cons 'title *autolisp-reference-value*) *autolisp-reference-entry*))

(setq *autolisp-reference-value* "grread")

(setq *autolisp-reference-entry* (cons (cons 'name *autolisp-reference-value*) *autolisp-reference-entry*))

(setq *autolisp-reference-parts* (cons (list (cons "grread" *autolisp-reference-entry*)) *autolisp-reference-parts*))

(setq *autolisp-reference-parts*
  (cons
    '(("grtext" .
          ((name . "grtext")
           (title . "grtext (AutoLISP)")
           (summary . "Writes text to the status line or to screen menu areas")
           (source-kind . "AutoLISP")
           (alphabetic-group . "G")
           (feature-groups . ("Display Control"))
           (supported-platforms . "Windows and Mac OS")
           (signature . "(grtext [box text [highlight]])")
           (arguments . (("box" . "Type: Integer\nLocation in which to write the text.")
                           ("text" . "Type: String\nSpecifies the text to be written to the screen menu or status line location. The text argument is truncated if it is too long to fit in the available area.")
                           ("highlight" . "Type: Integer\nSelects or deselects a screen menu location.")))
           (return-values . "Type: String\nThe string passed in the text argument, if successful, and nil if unsuccessful or no arguments are supplied.")
           (release-information . nil)
           (history . nil)
           (examples . "N/A")
           (url . "https://help.autodesk.com/cloudhelp/2023/ENU/AutoCAD-AutoLISP-Reference/files/GUID-5B0B01CA-BDBA-4A77-B840-6EE64591AC47.htm")
           (guid . "GUID-5B0B01CA-BDBA-4A77-B840-6EE64591AC47"))))
    *autolisp-reference-parts*))

(setq *autolisp-reference-entry* nil)

(setq *autolisp-reference-value* "GUID-44B8C277-4140-4F4C-ACF2-3332CC463021")

(setq *autolisp-reference-entry* (cons (cons 'guid *autolisp-reference-value*) *autolisp-reference-entry*))

(setq *autolisp-reference-value* "https://help.autodesk.com/cloudhelp/2023/ENU/AutoCAD-AutoLISP-Reference/files/GUID-44B8C277-4140-4F4C-ACF2-3332CC463021.htm")

(setq *autolisp-reference-entry* (cons (cons 'url *autolisp-reference-value*) *autolisp-reference-entry*))

(setq *autolisp-reference-value* "The following code draws five vertical lines in the drawing area, each a different color:\n\n(grvecs '(1 (1 2)(1 5)       Draws a red line from (1,2) to (1,5)\n          2 (2 2)(2 5)       Draws a yellow line from (2,2) to (2,5)\n          3 (3 2)(3 5)       Draws a green line from (3,2) to (3,5)\n          4 (4 2)(4 5)       Draws a cyan line from (4,2) to (4,5)\n          5 (5 2)(5 5)       Draws a blue line from (5,2) to (5,5)\n) )\n\nThe following matrix represents a uniform scale of 1.0 and a translation of 5.0,5.0,0.0. If this matrix is applied to the preceding list of vectors, they will be offset by 5.0,5.0,0.0.\n\n'((1.0 0.0 0.0 5.0)\n   (0.0 1.0 0.0 5.0)\n   (0.0 0.0 1.0 0.0)\n   (0.0 0.0 0.0 1.0)\n)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: nil\nAlways returns nil.")

(setq *autolisp-reference-entry* (cons (cons 'return-values *autolisp-reference-value*) *autolisp-reference-entry*))

(setq *autolisp-reference-value* nil)

(setq *autolisp-reference-string* "Type: List\nA transformation matrix used to change the location or proportion of the vectors defined in your vector list. This matrix is a list of four lists of four real numbers.")

(setq *autolisp-reference-value* (cons (cons "trans" *autolisp-reference-string*) *autolisp-reference-value*))

(setq *autolisp-reference-string* "Type: List\nA vector list is composed of a series of optional color integers and two point lists. See below for details on how to format vlist.")

(setq *autolisp-reference-value* (cons (cons "vlist" *autolisp-reference-string*) *autolisp-reference-value*))

(setq *autolisp-reference-entry* (cons (cons 'arguments *autolisp-reference-value*) *autolisp-reference-entry*))

(setq *autolisp-reference-value* "(grvecs vlist [trans])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Display Control"))

(setq *autolisp-reference-entry* (cons (cons 'feature-groups *autolisp-reference-value*) *autolisp-reference-entry*))

(setq *autolisp-reference-value* "G")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Draws multiple vectors in the drawing area")

(setq *autolisp-reference-entry* (cons (cons 'summary *autolisp-reference-value*) *autolisp-reference-entry*))

(setq *autolisp-reference-value* "grvecs (AutoLISP)")

(setq *autolisp-reference-entry* (cons (cons 'title *autolisp-reference-value*) *autolisp-reference-entry*))

(setq *autolisp-reference-value* "grvecs")

(setq *autolisp-reference-entry* (cons (cons 'name *autolisp-reference-value*) *autolisp-reference-entry*))

(setq *autolisp-reference-parts* (cons (list (cons "grvecs" *autolisp-reference-entry*)) *autolisp-reference-parts*))

(setq *autolisp-reference-parts*
  (cons
    '(("handent" .
          ((name . "handent")
           (title . "handent (AutoLISP)")
           (summary . "Returns an object (entity) name based on its handle")
           (source-kind . "AutoLISP")
           (alphabetic-group . "H")
           (feature-groups . ("Object-Handling"))
           (supported-platforms . "Windows and Mac OS")
           (signature . "(handent handle)")
           (arguments . (("handle" . "Type: String\nA string identifying an entity handle.")))
           (return-values . "Type: Ename (entity name) or nil\nIf successful, handent returns the entity name associated with handle in the current editing session. If handent is passed an invalid handle or a handle not used by any entity in the current drawing, it returns nil.\nThe handent function returns entities that have been deleted during the current editing session. You can undelete them with the entdel function.\nAn entity's name can change from one editing session to the next, but an entity's handle remains constant.")
           (release-information . nil)
           (history . nil)
           (examples . "(handent \"5A2\")\n<Entity name: 60004722>\n\nUsed with the same drawing but in another editing session, the same call might return a different entity name. Once the entity name is obtained, you can use it to manipulate the entity with any of the entity-related functions.")
           (url . "https://help.autodesk.com/cloudhelp/2023/ENU/AutoCAD-AutoLISP-Reference/files/GUID-AF6DD533-1A24-4687-96EB-F03F26050C07.htm")
           (guid . "GUID-AF6DD533-1A24-4687-96EB-F03F26050C07"))))
    *autolisp-reference-parts*))

(setq *autolisp-reference-entry* nil)

(setq *autolisp-reference-value* "GUID-4CB4A951-1507-4F3D-9F7B-93FF3A2C9850")

(setq *autolisp-reference-entry* (cons (cons 'guid *autolisp-reference-value*) *autolisp-reference-entry*))

(setq *autolisp-reference-value* "https://help.autodesk.com/cloudhelp/2023/ENU/AutoCAD-AutoLISP-Reference/files/GUID-4CB4A951-1507-4F3D-9F7B-93FF3A2C9850.htm")

(setq *autolisp-reference-entry* (cons (cons 'url *autolisp-reference-value*) *autolisp-reference-entry*))

(setq *autolisp-reference-value* "The following code calls help to display the information on MYCOMMAND in the Help file achelp.chm:\n\n(help \"achelp.chm\" \"mycommand\")")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String or nil\nThe helpfile string, if successful; otherwise nil. If you use help without any arguments, it returns an empty string (\"\") if successful, and nil if it fails.\nThe only error condition that the help function returns to the application is the existence of the file specified by helpfile. All other error conditions are reported to the user through a dialog box.")

(setq *autolisp-reference-entry* (cons (cons 'return-values *autolisp-reference-value*) *autolisp-reference-entry*))

(setq *autolisp-reference-value* nil)

(setq *autolisp-reference-string* "Type: String\nSpecifies the initial state of the Help window. The command argument is a string used by the uCommand (in HTML Help) or the fuCommand (in WinHelp) argument of the HtmlHelp() and WinHelp() functions as defined in the Microsoft Windows SDK.\nFor HTML Help files, the command parameter can be HH_ALINK_LOOKUP or HH_DISPLAY_TOPIC. For Windows Help files, the command parameter can be HELP_CONTENTS, HELP_HELPONHELP, or HELP_PARTIALKEY.")

(setq *autolisp-reference-value* (cons (cons "command (Windows only)" *autolisp-reference-string*) *autolisp-reference-value*))

(setq *autolisp-reference-string* "Type: String\nHelp topic ID.\nIf you are calling a topic within a CHM file, provide the file name without the extension; AutoCAD adds an .htm extension.")

(setq *autolisp-reference-value* (cons (cons "topic" *autolisp-reference-string*) *autolisp-reference-value*))

(setq *autolisp-reference-string* "Type: String\nHelp file name. The file extension is not required with the helpfile argument. If a file extension is provided, AutoCAD looks only for a file with the exact name specified.\nIf no file extension is provided, AutoCAD looks for helpfile with an extension of .chm. If no file of that name is found, AutoCAD looks for a file with an extension of .hlp.")

(setq *autolisp-reference-value* (cons (cons "helpfile" *autolisp-reference-string*) *autolisp-reference-value*))

(setq *autolisp-reference-entry* (cons (cons 'arguments *autolisp-reference-value*) *autolisp-reference-entry*))

(setq *autolisp-reference-value* "(help [helpfile [topic [command]]])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Query and Command"))

(setq *autolisp-reference-entry* (cons (cons 'feature-groups *autolisp-reference-value*) *autolisp-reference-entry*))

(setq *autolisp-reference-value* "H")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Invokes the Help facility")

(setq *autolisp-reference-entry* (cons (cons 'summary *autolisp-reference-value*) *autolisp-reference-entry*))

(setq *autolisp-reference-value* "help (AutoLISP)")

(setq *autolisp-reference-entry* (cons (cons 'title *autolisp-reference-value*) *autolisp-reference-entry*))

(setq *autolisp-reference-value* "help")

(setq *autolisp-reference-entry* (cons (cons 'name *autolisp-reference-value*) *autolisp-reference-entry*))

(setq *autolisp-reference-parts* (cons (list (cons "help" *autolisp-reference-entry*)) *autolisp-reference-parts*))

(setq *autolisp-reference-parts*
  (cons
    '(("if" .
          ((name . "if")
           (title . "if (AutoLISP)")
           (summary . "Conditionally evaluates expressions")
           (source-kind . "AutoLISP")
           (alphabetic-group . "I")
           (feature-groups . ("Equality and Conditional"))
           (supported-platforms . "Windows and Mac OS")
           (signature . "(if testexpr thenexpr [elseexpr])")
           (arguments . (("testexpr" . "Type: Integer, Real, String, List, Ename (entity name), T, or nil\nExpression to be tested.")
                           ("thenexpr" . "Type: Integer, Real, String, List, Ename (entity name), T, or nil\nExpression evaluated if testexpr is not nil.")
                           ("elseexpr" . "Type: Integer, Real, String, List, Ename (entity name), T, or nil\nExpression evaluated if testexpr is nil.")))
           (return-values . "Type: Integer, Real, String, List, Ename (entity name), T, or nil\nThe if function returns the value of the selected expression. If elseexpr is missing and testexpr is nil, then it returns nil.")
           (release-information . nil)
           (history . nil)
           (examples . "(if (= 1 3) \"YES!!\" \"no.\")\n\"no.\"\n\n(if (= 2 (+ 1 1)) \"YES!!\")\n\"YES!!\"\n\n(if (= 2 (+ 3 4)) \"YES!!\")\nnil")
           (url . "https://help.autodesk.com/cloudhelp/2023/ENU/AutoCAD-AutoLISP-Reference/files/GUID-916F1A5C-FD70-4D66-897E-6DCD666DCB39.htm")
           (guid . "GUID-916F1A5C-FD70-4D66-897E-6DCD666DCB39"))))
    *autolisp-reference-parts*))

(setq *autolisp-reference-entry* nil)

(setq *autolisp-reference-value* "GUID-6176FC98-DC5D-433E-8D76-F481BE68D46A")

(setq *autolisp-reference-entry* (cons (cons 'guid *autolisp-reference-value*) *autolisp-reference-entry*))

(setq *autolisp-reference-value* "https://help.autodesk.com/cloudhelp/2023/ENU/AutoCAD-AutoLISP-Reference/files/GUID-6176FC98-DC5D-433E-8D76-F481BE68D46A.htm")

(setq *autolisp-reference-entry* (cons (cons 'url *autolisp-reference-value*) *autolisp-reference-entry*))

(setq *autolisp-reference-value* "Initializing a specific command version may affect each supported command differently. For example, here is the AutoCAD FILLET command with and without an initialized version:\n\nCommand: FILLET\n\nCurrent settings: Mode = TRIM, Radius = 0.0000\n\nSelect first object or [Undo/Polyline/Radius/Trim/Multiple]: *Cancel*\n\nCommand: (initcommandversion 1)\n\nCommand: FILLET\n\nCurrent settings: Mode = TRIM, Radius = 0.0000\n\nSelect first object or [uNdo/Polyline/Radius/Trim/mUltiple]: *Cancel*\n\nAnother typical example is the AutoCAD COLOR command. Run normally, COLOR displays the Select Color dialog; but by running (initcommandversion 1) before the COLOR command, it is forced to prompt from color from the Command prompt.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T\nAlways returns T.")

(setq *autolisp-reference-entry* (cons (cons 'return-values *autolisp-reference-value*) *autolisp-reference-entry*))

(setq *autolisp-reference-value* nil)

(setq *autolisp-reference-string* "Type: Integer\nThis argument specifies the version of the command to be used. If this argument is not present, the next use (and next use only) of a supported command will initialize to the latest version.")

(setq *autolisp-reference-value* (cons (cons "version" *autolisp-reference-string*) *autolisp-reference-value*))

(setq *autolisp-reference-entry* (cons (cons 'arguments *autolisp-reference-value*) *autolisp-reference-entry*))

(setq *autolisp-reference-value* "(initcommandversion [version])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* nil)

(setq *autolisp-reference-entry* (cons (cons 'feature-groups *autolisp-reference-value*) *autolisp-reference-entry*))

(setq *autolisp-reference-value* "I")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Forces the next command to run with the specified version")

(setq *autolisp-reference-entry* (cons (cons 'summary *autolisp-reference-value*) *autolisp-reference-entry*))

(setq *autolisp-reference-value* "initcommandversion (AutoLISP)")

(setq *autolisp-reference-entry* (cons (cons 'title *autolisp-reference-value*) *autolisp-reference-entry*))

(setq *autolisp-reference-value* "initcommandversion")

(setq *autolisp-reference-entry* (cons (cons 'name *autolisp-reference-value*) *autolisp-reference-entry*))

(setq *autolisp-reference-parts* (cons (list (cons "initcommandversion" *autolisp-reference-entry*)) *autolisp-reference-parts*))

(setq *autolisp-reference-parts*
  (cons
    '(("initdia" .
          ((name . "initdia")
           (title . "initdia (AutoLISP)")
           (summary . "Forces the display of the next command's dialog box")
           (source-kind . "AutoLISP")
           (alphabetic-group . "I")
           (feature-groups . ("Application-Handling"))
           (supported-platforms . "Windows and Mac OS")
           (signature . "(initdia [dialogflag])")
           (arguments . (("dialogflag" . "Type: Integer\nA numeric value. If this argument is not present or is present and nonzero, the next use (and next use only) of a command will display that command's dialog box rather than its command line prompts.\nIf dialogflag is zero, any previous call to this function is cleared, restoring the default behavior of presenting the command line interface.")))
           (return-values . "Type: nil\nAlways returns nil.")
           (release-information . nil)
           (history . nil)
           (examples . "Issue the PLOT command without calling initdia first:\n\nCommand: (command \"._plot\")\n\nplot\n\nEnter a layout name <Model>: nil\n\nEnter a layout name <Model>:\n\nAutoCAD prompts for user input in the command window.\n\nUse the following sequence of function calls to make AutoCAD display the Plot dialog box:\n\n(initdia)\n(command \"._plot\")")
           (url . "https://help.autodesk.com/cloudhelp/2023/ENU/AutoCAD-AutoLISP-Reference/files/GUID-D0F621C5-6D32-4D79-BC49-290CC4D0FDB8.htm")
           (guid . "GUID-D0F621C5-6D32-4D79-BC49-290CC4D0FDB8"))))
    *autolisp-reference-parts*))

(setq *autolisp-reference-entry* nil)

(setq *autolisp-reference-value* "GUID-9ED8841B-5C1D-4B3F-9F3B-84A4408A6BBF")

(setq *autolisp-reference-entry* (cons (cons 'guid *autolisp-reference-value*) *autolisp-reference-entry*))

(setq *autolisp-reference-value* "https://help.autodesk.com/cloudhelp/2023/ENU/AutoCAD-AutoLISP-Reference/files/GUID-9ED8841B-5C1D-4B3F-9F3B-84A4408A6BBF.htm")

(setq *autolisp-reference-entry* (cons (cons 'url *autolisp-reference-value*) *autolisp-reference-entry*))

(setq *autolisp-reference-value* "None")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: nil\nAlways returns nil.")

(setq *autolisp-reference-entry* (cons (cons 'return-values *autolisp-reference-value*) *autolisp-reference-entry*))

(setq *autolisp-reference-value* nil)

(setq *autolisp-reference-string* "Type: String\nSeries of keywords.")

(setq *autolisp-reference-value* (cons (cons "keywords" *autolisp-reference-string*) *autolisp-reference-value*))

(setq *autolisp-reference-string* "Type: Integer\nA bit-coded that allows or disallows certain types of user input. The bits can be added together in any combination to form a value between 0 and 255. If no bits argument is supplied, zero (no conditions) is assumed. The bit values are as follows:\n1 (bit 0) -- Prevents the user from responding to the request by entering only Enter.\n2 (bit 1) -- Prevents the user from responding to the request by entering zero.\n4 (bit 2) -- Prevents the user from responding to the request by entering a negative value.\n8 (bit 3) -- Allows the user to enter a point outside the current drawing limits. This condition applies to the next user-input function even if the AutoCAD LIMCHECK system variable is currently set.\n16 (bit 4) -- (Not currently used.)\n32 (bit 5) -- Uses dashed lines when drawing a rubber-band line or box. For those functions with which the user can specify a point by se")

(setq *autolisp-reference-string* (strcat *autolisp-reference-string* "lecting a location in the drawing area, this bit value causes the rubber-band line or box to be dashed instead of solid. (Some display drivers use a distinctive color instead of dashed lines.) If the AutoCAD POPUPS system variable is 0, AutoCAD ignores this bit.\n64 (bit 6) -- Prohibits input of a Z coordinate to the getdist function; lets an application ensure that this function returns a 2D distance.\n128 (bit 7) -- Allows arbitrary input as if it is a keyword, first honoring any other control bits and listed keywords. This bit takes precedence over bit 0; if bits 7 and 0 are set and the user presses Enter, a null string is returned.\n256 (bit 8) -- Give direct distance input precedence over arbitrary input. For external applications, arbitrary input is given precedence over direct distance input by default. Set this bit if you wish to force AutoCAD to evaluate user input as direct dis"))

(setq *autolisp-reference-string* (strcat *autolisp-reference-string* "tance input. Note that legal point input from the keyboard always takes precedence over either direct distance or arbitrary input.\n512 (bit 9) -- If set before a call to getpoint or getcorner, a temporary UCS will be established when the cursor crosses over the edge of a planar face of a solid. The temporary UCS is reset when the cursor moves off of a face. It is dynamically re-established when the cursor moves over a different face. After the point is acquired, the dynamic UCS is reset to the current UCS. This functionality is not enabled for non-planar faces such as the side of a cylinder.\n1024 (bit 10) -- When calling getdist, getangle, getorient, getpoint, or getcorner, you may not want the distance, angle, orient, point, or corner to be influenced by ortho, polar, or otracking in the Z direction. Setting this bit before calls to any of these functions will temporarily disable orth"))

(setq *autolisp-reference-string* (strcat *autolisp-reference-string* "o, polar, and otracking in the Z direction. This is useful when you create 2D entities such as a polyline, arc, or circle, or when you use the AutoCAD ARRAY command, which creates only a 2D array. In 2D-only commands it can be confusing and error-prone to allow 3D points to be entered using ortho Z, polar Z, or otrack Z.\nNote: Future versions of AutoLISP may use additional initget control bits, so avoid setting bits that are not listed here."))

(setq *autolisp-reference-value* (cons (cons "bits" *autolisp-reference-string*) *autolisp-reference-value*))

(setq *autolisp-reference-entry* (cons (cons 'arguments *autolisp-reference-value*) *autolisp-reference-entry*))

(setq *autolisp-reference-value* "(initget [bits] [keywords])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("User Input"))

(setq *autolisp-reference-entry* (cons (cons 'feature-groups *autolisp-reference-value*) *autolisp-reference-entry*))

(setq *autolisp-reference-value* "I")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Establishes keywords for use by the next user-input function call")

(setq *autolisp-reference-entry* (cons (cons 'summary *autolisp-reference-value*) *autolisp-reference-entry*))

(setq *autolisp-reference-value* "initget (AutoLISP)")

(setq *autolisp-reference-entry* (cons (cons 'title *autolisp-reference-value*) *autolisp-reference-entry*))

(setq *autolisp-reference-value* "initget")

(setq *autolisp-reference-entry* (cons (cons 'name *autolisp-reference-value*) *autolisp-reference-entry*))

(setq *autolisp-reference-parts* (cons (list (cons "initget" *autolisp-reference-entry*)) *autolisp-reference-parts*))

(setq *autolisp-reference-entry* nil)

(setq *autolisp-reference-value* "GUID-A181D474-F817-4550-86E9-87649262FA8A")

(setq *autolisp-reference-entry* (cons (cons 'guid *autolisp-reference-value*) *autolisp-reference-entry*))

(setq *autolisp-reference-value* "https://help.autodesk.com/cloudhelp/2023/ENU/AutoCAD-AutoLISP-Reference/files/GUID-A181D474-F817-4550-86E9-87649262FA8A.htm")

(setq *autolisp-reference-entry* (cons (cons 'url *autolisp-reference-value*) *autolisp-reference-entry*))

(setq *autolisp-reference-value* "(setq a '(1.0 1.0) b '(9.0 9.0))\n(setq c '(4.0 1.0) d '(4.0 2.0))\n\n(inters a b c d)\nnil\n\n(inters a b c d T)\nnil\n\n(inters a b c d nil)\n(4.0 4.0)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nIf the onseg argument is present and is nil, inters returns the point where the lines intersect, even if that point is off the end of one or both of the lines. If the onseg argument is omitted or is not nil, the intersection point must lie on both lines or inters returns nil. The inters function returns nil if the two lines do not intersect.")

(setq *autolisp-reference-entry* (cons (cons 'return-values *autolisp-reference-value*) *autolisp-reference-entry*))

(setq *autolisp-reference-value* nil)

(setq *autolisp-reference-string* "Type: List or nil\nIf specified as nil, the lines defined by the four pt arguments are considered infinite in length. If the onseg argument is omitted or is not nil, the intersection point must lie on both lines or inters returns nil.")

(setq *autolisp-reference-value* (cons (cons "onseg" *autolisp-reference-string*) *autolisp-reference-value*))

(setq *autolisp-reference-string* "Type: List\nThe other endpoint of the second line.")

(setq *autolisp-reference-value* (cons (cons "pt4" *autolisp-reference-string*) *autolisp-reference-value*))

(setq *autolisp-reference-string* "Type: List\nOne endpoint of the second line.")

(setq *autolisp-reference-value* (cons (cons "pt3" *autolisp-reference-string*) *autolisp-reference-value*))

(setq *autolisp-reference-string* "Type: List\nThe other endpoint of the first line.")

(setq *autolisp-reference-value* (cons (cons "pt2" *autolisp-reference-string*) *autolisp-reference-value*))

(setq *autolisp-reference-string* "Type: List\nOne endpoint of the first line.")

(setq *autolisp-reference-value* (cons (cons "pt1" *autolisp-reference-string*) *autolisp-reference-value*))

(setq *autolisp-reference-entry* (cons (cons 'arguments *autolisp-reference-value*) *autolisp-reference-entry*))

(setq *autolisp-reference-value* "(inters pt1 pt2 pt3 pt4 [onseg])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Geometric"))

(setq *autolisp-reference-entry* (cons (cons 'feature-groups *autolisp-reference-value*) *autolisp-reference-entry*))

(setq *autolisp-reference-value* "I")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Finds the intersection of two lines")

(setq *autolisp-reference-entry* (cons (cons 'summary *autolisp-reference-value*) *autolisp-reference-entry*))

(setq *autolisp-reference-value* "inters (AutoLISP)")

(setq *autolisp-reference-entry* (cons (cons 'title *autolisp-reference-value*) *autolisp-reference-entry*))

(setq *autolisp-reference-value* "inters")

(setq *autolisp-reference-entry* (cons (cons 'name *autolisp-reference-value*) *autolisp-reference-entry*))

(setq *autolisp-reference-parts* (cons (list (cons "inters" *autolisp-reference-entry*)) *autolisp-reference-parts*))

(setq *autolisp-reference-entry* nil)

(setq *autolisp-reference-value* "GUID-1DE8095D-5755-4889-BFB7-C13045B7BC81")

(setq *autolisp-reference-entry* (cons (cons 'guid *autolisp-reference-value*) *autolisp-reference-entry*))

(setq *autolisp-reference-value* "https://help.autodesk.com/cloudhelp/2023/ENU/AutoCAD-AutoLISP-Reference/files/GUID-1DE8095D-5755-4889-BFB7-C13045B7BC81.htm")

(setq *autolisp-reference-entry* (cons (cons 'url *autolisp-reference-value*) *autolisp-reference-entry*))

(setq *autolisp-reference-value* "The following example demonstrates how to check the read-only state of the Radius and Area properties of a circle.\n\n(setq e1 (car (entsel \"\\nSelect an arc or circle: \")))\n<Entity name: 10e2e4ba0>\n\n(ispropertyreadonly e1 \"Radius\")\n0\n\n(ispropertyreadonly e1 \"Area\")\n1")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer\n1 is returned when the property is read-only; otherwise, 0 is returned when the property is writable.")

(setq *autolisp-reference-entry* (cons (cons 'return-values *autolisp-reference-value*) *autolisp-reference-entry*))

(setq *autolisp-reference-value* nil)

(setq *autolisp-reference-string* "Type: String\nThe name of the property within the collection being queried.")

(setq *autolisp-reference-value* (cons (cons "name" *autolisp-reference-string*) *autolisp-reference-value*))

(setq *autolisp-reference-string* "Type: Integer\nThe collection index being queried.")

(setq *autolisp-reference-value* (cons (cons "index" *autolisp-reference-string*) *autolisp-reference-value*))

(setq *autolisp-reference-string* "Type: String\nIf the object is a collection object, the Collection name is passed here.")

(setq *autolisp-reference-value* (cons (cons "collectionName" *autolisp-reference-string*) *autolisp-reference-value*))

(setq *autolisp-reference-string* "Type: String\nName of the property being queried. For a list of all the valid property names of a given object, use dumpallproperties.")

(setq *autolisp-reference-value* (cons (cons "propertyname" *autolisp-reference-string*) *autolisp-reference-value*))

(setq *autolisp-reference-string* "Type: Ename (entity name)\nName of the entity being queried. The ename can refer to either a graphical or a non-graphical entity.")

(setq *autolisp-reference-value* (cons (cons "ename" *autolisp-reference-string*) *autolisp-reference-value*))

(setq *autolisp-reference-entry* (cons (cons 'arguments *autolisp-reference-value*) *autolisp-reference-entry*))

(setq *autolisp-reference-value* "(ispropertyreadonly ename propertyname [or collectionName index name])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Object-Handling"))

(setq *autolisp-reference-entry* (cons (cons 'feature-groups *autolisp-reference-value*) *autolisp-reference-entry*))

(setq *autolisp-reference-value* "I")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns the read-only state of an entity’s property")

(setq *autolisp-reference-entry* (cons (cons 'summary *autolisp-reference-value*) *autolisp-reference-entry*))

(setq *autolisp-reference-value* "ispropertyreadonly (AutoLISP)")

(setq *autolisp-reference-entry* (cons (cons 'title *autolisp-reference-value*) *autolisp-reference-entry*))

(setq *autolisp-reference-value* "ispropertyreadonly")

(setq *autolisp-reference-entry* (cons (cons 'name *autolisp-reference-value*) *autolisp-reference-entry*))

(setq *autolisp-reference-parts* (cons (list (cons "ispropertyreadonly" *autolisp-reference-entry*)) *autolisp-reference-parts*))

(setq *autolisp-reference-parts*
  (cons
    '(("itoa" .
          ((name . "itoa")
           (title . "itoa (AutoLISP)")
           (summary . "Returns the conversion of an integer into a string")
           (source-kind . "AutoLISP")
           (alphabetic-group . "I")
           (feature-groups . ("Conversion"))
           (supported-platforms . "Windows and Mac OS")
           (signature . "(itoa int)")
           (arguments . (("int" . "Type: Integer\nA numeric value.")))
           (return-values . "Type: String\nA string derived from int.")
           (release-information . nil)
           (history . nil)
           (examples . "(itoa 33)\n\"33\"\n\n(itoa -17)\n\"-17\"")
           (url . "https://help.autodesk.com/cloudhelp/2023/ENU/AutoCAD-AutoLISP-Reference/files/GUID-7E247CA3-95D3-4497-BDE2-6EB0E727DD4D.htm")
           (guid . "GUID-7E247CA3-95D3-4497-BDE2-6EB0E727DD4D"))))
    *autolisp-reference-parts*))

(setq *autolisp-reference-parts*
  (cons
    '(("lambda" .
          ((name . "lambda")
           (title . "lambda (AutoLISP)")
           (summary . "Defines an anonymous function")
           (source-kind . "AutoLISP")
           (alphabetic-group . "L")
           (feature-groups . ("Function-Handling"))
           (supported-platforms . "Windows and Mac OS")
           (signature . "(lambda arguments expr ...)")
           (arguments . (("arguments" . "Type: List\nArguments passed to an expression.")
                           ("expr" . "Type: List\nAn AutoLISP expression.")))
           (return-values . "Type: Integer, Real, String, List, Symbol, Ename (entity name), T, or nil\nValue of the last expr.")
           (release-information . nil)
           (history . nil)
           (examples . "The following examples demonstrate the lambda function:\n\n(apply '(lambda (x y z)\n          (* x (- y z))\n        )\n        '(5 20 14)\n)\n30\n\n(setq counter 0)\n(mapcar '(lambda (x)\n          (setq counter (1+ counter))\n          (* x 5)\n        )\n        '(2 4 -6 10.2)\n)\n0\n(10 20 -30 51.0)")
           (url . "https://help.autodesk.com/cloudhelp/2023/ENU/AutoCAD-AutoLISP-Reference/files/GUID-3B8BB020-1E1A-4FA3-B7B3-B5B20BA04CD9.htm")
           (guid . "GUID-3B8BB020-1E1A-4FA3-B7B3-B5B20BA04CD9"))))
    *autolisp-reference-parts*))

(setq *autolisp-reference-parts*
  (cons
    '(("last" .
          ((name . "last")
           (title . "last (AutoLISP)")
           (summary . "Returns the last element in a list")
           (source-kind . "AutoLISP")
           (alphabetic-group . "L")
           (feature-groups . ("List Manipulation"))
           (supported-platforms . "Windows and Mac OS")
           (signature . "(last lst)")
           (arguments . (("lst" . "Type: List\nA list of one or more elements.")))
           (return-values . "Type: Integer, Real, String, List, Ename (entity name), T, or nil\nAn atom or a list.")
           (release-information . nil)
           (history . nil)
           (examples . "(last '(a b c d e))\nE\n\n(last '(a b c (d e)))\n(D E)")
           (url . "https://help.autodesk.com/cloudhelp/2023/ENU/AutoCAD-AutoLISP-Reference/files/GUID-463C97F2-B72F-44C6-B19B-659D231AA836.htm")
           (guid . "GUID-463C97F2-B72F-44C6-B19B-659D231AA836"))))
    *autolisp-reference-parts*))

(setq *autolisp-reference-entry* nil)

(setq *autolisp-reference-value* "GUID-F392F4F2-B2C1-4C8E-AEBB-1D3FE31610C9")

(setq *autolisp-reference-entry* (cons (cons 'guid *autolisp-reference-value*) *autolisp-reference-entry*))

(setq *autolisp-reference-value* "https://help.autodesk.com/cloudhelp/2023/ENU/AutoCAD-AutoLISP-Reference/files/GUID-F392F4F2-B2C1-4C8E-AEBB-1D3FE31610C9.htm")

(setq *autolisp-reference-entry* (cons (cons 'url *autolisp-reference-value*) *autolisp-reference-entry*))

(setq *autolisp-reference-value* "(layerstate-addlayers\n  \"myLayerState\"\n  (list \"Walls\" 4 '(62 . 45) \"Divide\" 35 \"10% Screen\")\n  (list \"Floors\" 6 '(420 . 16235019) \"Continuous\" 40 \"60% Screen\")\n  (list \"Ceiling\" 0 '(430 . \"RAL CLASSIC$RAL 1003\") \"DOT\" nil nil)\n)\nT")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nT if successful; otherwise nil.")

(setq *autolisp-reference-entry* (cons (cons 'return-values *autolisp-reference-value*) *autolisp-reference-entry*))

(setq *autolisp-reference-value* nil)

(setq *autolisp-reference-string* "Type: String\nName of the layers plot style. The plotstyle name must already be loaded in the drawing or the default of \"Normal\" will be used. A nil value sets the layer plotstyle to \"Normal.\" If the drawing is in color dependent mode, this setting is ignored.")

(setq *autolisp-reference-value* (cons (cons "plotstyle" *autolisp-reference-string*) *autolisp-reference-value*))

(setq *autolisp-reference-string* "Type: Integer\nNumber corresponding to a valid lineweight, i.e., 35 = .35, 211 = 2.11. A nil value sets the layer lineweight to \"Default.\"")

(setq *autolisp-reference-value* (cons (cons "lineweight" *autolisp-reference-string*) *autolisp-reference-value*))

(setq *autolisp-reference-string* "Type: String\nName of the layer linetype. The linetype must already be loaded in the drawing or the default of \"Continuous\" will be used. A nil value sets the layer linetype to \"Continuous.\"")

(setq *autolisp-reference-value* (cons (cons "linetype" *autolisp-reference-string*) *autolisp-reference-value*))

(setq *autolisp-reference-string* "Type: List\nA dotted pair specifying the layers color type and value, e.g. (62 . ColorIndex), (420 . TrueColor), or (430 . \"colorbook$colorname\").")

(setq *autolisp-reference-value* (cons (cons "color" *autolisp-reference-string*) *autolisp-reference-value*))

(setq *autolisp-reference-string* "Type: Integer or nil\nNumeric sum designating properties in the layer to be set.\n1 -- Turns the layer off\n2 -- Freeze the layer\n4 -- Lock the layer\n8 -- Flag the layer as No Plot\n16 -- Set the layer as being frozen in new viewports\nA nil value uses defaults of on, thawed, unlocked, plottable, and thawed in new viewports.")

(setq *autolisp-reference-value* (cons (cons "state" *autolisp-reference-string*) *autolisp-reference-value*))

(setq *autolisp-reference-string* "Type: String\nName of the layer to be added or updated.")

(setq *autolisp-reference-value* (cons (cons "layername" *autolisp-reference-string*) *autolisp-reference-value*))

(setq *autolisp-reference-string* "Type: String\nName of the layer state to be updated.")

(setq *autolisp-reference-value* (cons (cons "layerstatename" *autolisp-reference-string*) *autolisp-reference-value*))

(setq *autolisp-reference-entry* (cons (cons 'arguments *autolisp-reference-value*) *autolisp-reference-entry*))

(setq *autolisp-reference-value* "(layerstate-addlayers layerstatename (list layername state color linetype lineweight plotstyle) [(list ...)])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* nil)

(setq *autolisp-reference-entry* (cons (cons 'feature-groups *autolisp-reference-value*) *autolisp-reference-entry*))

(setq *autolisp-reference-value* "L")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Adds or updates a series of layers to a layer state")

(setq *autolisp-reference-entry* (cons (cons 'summary *autolisp-reference-value*) *autolisp-reference-entry*))

(setq *autolisp-reference-value* "layerstate-addlayers (AutoLISP)")

(setq *autolisp-reference-entry* (cons (cons 'title *autolisp-reference-value*) *autolisp-reference-entry*))

(setq *autolisp-reference-value* "layerstate-addlayers")

(setq *autolisp-reference-entry* (cons (cons 'name *autolisp-reference-value*) *autolisp-reference-entry*))

(setq *autolisp-reference-parts* (cons (list (cons "layerstate-addlayers" *autolisp-reference-entry*)) *autolisp-reference-parts*))

(setq *autolisp-reference-parts*
  (cons
    '(("layerstate-compare" .
          ((name . "layerstate-compare")
           (title . "layerstate-compare (AutoLISP)")
           (summary . "Compares a layer state to the layers in the current drawing")
           (source-kind . "AutoLISP")
           (alphabetic-group . "L")
           (feature-groups . nil)
           (supported-platforms . "Windows and Mac OS")
           (signature . "(layerstate-compare layerstatename viewport)")
           (arguments . (("layerstatename" . "Type: String\nName of the layer state compare.")
                           ("viewport" . "Type: Ename (entity name)\nAn ename of the viewport to be used in the compare. If viewport is nil, the current viewport is used")))
           (return-values . "Type: T or nil\nT if successful; otherwise nil.")
           (release-information . nil)
           (history . nil)
           (examples . "(layerstate-compare \"myLayerState\")\nnil")
           (url . "https://help.autodesk.com/cloudhelp/2023/ENU/AutoCAD-AutoLISP-Reference/files/GUID-C2555813-0DD3-46AA-B22F-3F0D479922C3.htm")
           (guid . "GUID-C2555813-0DD3-46AA-B22F-3F0D479922C3"))))
    *autolisp-reference-parts*))

(setq *autolisp-reference-parts*
  (cons
    '(("layerstate-delete" .
          ((name . "layerstate-delete")
           (title . "layerstate-delete (AutoLISP)")
           (summary . "Deletes a layer state")
           (source-kind . "AutoLISP")
           (alphabetic-group . "L")
           (feature-groups . nil)
           (supported-platforms . "Windows and Mac OS")
           (signature . "(layerstate-delete layerstatename)")
           (arguments . (("layerstatename" . "Type: String\nName of the layer state to be deleted.")))
           (return-values . "Type: T or nil\nT if the delete succeeds; otherwise nil.")
           (release-information . nil)
           (history . nil)
           (examples . "(layerstate-delete \"myLayerState\")\nT")
           (url . "https://help.autodesk.com/cloudhelp/2023/ENU/AutoCAD-AutoLISP-Reference/files/GUID-828C4B51-7C59-4FF0-AA69-907C53F31703.htm")
           (guid . "GUID-828C4B51-7C59-4FF0-AA69-907C53F31703"))))
    *autolisp-reference-parts*))

(setq *autolisp-reference-parts*
  (cons
    '(("layerstate-export" .
          ((name . "layerstate-export")
           (title . "layerstate-export (AutoLISP)")
           (summary . "Exports a layer state to a specified file")
           (source-kind . "AutoLISP")
           (alphabetic-group . "L")
           (feature-groups . nil)
           (supported-platforms . "Windows and Mac OS")
           (signature . "(layerstate-export layerstatename filename)")
           (arguments . (("layerstatename" . "Type: String\nName of the layer to export.")
                           ("filename" . "Type: String\nName of the file to which the layer state should be exported.")))
           (return-values . "Type: T or nil\nT if the export is successful; nil otherwise.")
           (release-information . nil)
           (history . nil)
           (examples . "Windows\n\n(layerstate-export \"myLayerState\" \"c:\\\\mylayerstate.las\")\nT\n\nMac OS\n\n(layerstate-export \"myLayerState\" \"/mylayerstate.las\")\nT")
           (url . "https://help.autodesk.com/cloudhelp/2023/ENU/AutoCAD-AutoLISP-Reference/files/GUID-E14DB236-6DD9-48A8-91F3-8A44A6E8BAA4.htm")
           (guid . "GUID-E14DB236-6DD9-48A8-91F3-8A44A6E8BAA4"))))
    *autolisp-reference-parts*))

(setq *autolisp-reference-parts*
  (cons
    '(("layerstate-getlastrestored" .
          ((name . "layerstate-getlastrestored")
           (title . "layerstate-getlastrestored (AutoLISP)")
           (summary . "Returns the name of the last restored layer state in the current drawing")
           (source-kind . "AutoLISP")
           (alphabetic-group . "L")
           (feature-groups . nil)
           (supported-platforms . "Windows and Mac OS")
           (signature . "(layerstate-getlastrestored)")
           (arguments . nil)
           (return-values . "Type: String or nil\nReturns the name of the last restored layer state in the current drawing.")
           (release-information . nil)
           (history . nil)
           (examples . "(layerstate-getlastrestored)\n\"Foundation\"")
           (url . "https://help.autodesk.com/cloudhelp/2023/ENU/AutoCAD-AutoLISP-Reference/files/GUID-404D79AB-B213-4EF4-A0A6-19F2E4F0A9A9.htm")
           (guid . "GUID-404D79AB-B213-4EF4-A0A6-19F2E4F0A9A9"))))
    *autolisp-reference-parts*))

(setq *autolisp-reference-parts*
  (cons
    '(("layerstate-getlayers" .
          ((name . "layerstate-getlayers")
           (title . "layerstate-getlayers (AutoLISP)")
           (summary . "Returns the layers saved in a layer state")
           (source-kind . "AutoLISP")
           (alphabetic-group . "L")
           (feature-groups . nil)
           (supported-platforms . "Windows and Mac OS")
           (signature . "(layerstate-getlayers layerstatename [invert])")
           (arguments . (("layerstatename" . "Type: String\nName of the layer state to query for layers.")
                           ("invert" . "Type: List or nil\nIf invert is omitted or nil, returns a list of the layers saved in the layer state. If invert is T, it returns a list of the layers in the drawing that are not saved in the layer state.")))
           (return-values . "Type: List or nil\nA list of layer names. Returns nil if the layer state does not exist or contains no layers.")
           (release-information . nil)
           (history . nil)
           (examples . "(layerstate-getlayers \"myLayerState\")\n(\"Layername1\" \"Layername2\")")
           (url . "https://help.autodesk.com/cloudhelp/2023/ENU/AutoCAD-AutoLISP-Reference/files/GUID-B0B12E74-D5EF-47E2-9B1C-ED595AA663A8.htm")
           (guid . "GUID-B0B12E74-D5EF-47E2-9B1C-ED595AA663A8"))))
    *autolisp-reference-parts*))

(setq *autolisp-reference-parts*
  (cons
    '(("layerstate-getnames" .
          ((name . "layerstate-getnames")
           (title . "layerstate-getnames (AutoLISP)")
           (summary . "Returns a list of the layer state names")
           (source-kind . "AutoLISP")
           (alphabetic-group . "L")
           (feature-groups . nil)
           (supported-platforms . "Windows and Mac OS")
           (signature . "(layerstate-getnames [includehidden] [includexref])")
           (arguments . (("includehidden" . "Type: T or nil\nIf includehidden is T, the list will include the names of hidden layer states. If omitted or nil, hidden layer states will be excluded.")
                           ("includexref" . "Type: T or nil\nIf includexref is nil, the list will exclude the names of xref layer states. If omitted or T, xref layer states will be included")))
           (return-values . "Type: List or nil\nReturns a list of the layer state names.")
           (release-information . nil)
           (history . nil)
           (examples . "(layerstate-getnames)\n(\"First Floor\" \"Second Floor\" \"Foundation\")")
           (url . "https://help.autodesk.com/cloudhelp/2023/ENU/AutoCAD-AutoLISP-Reference/files/GUID-B0EF0543-F792-4391-B54F-606F5685065C.htm")
           (guid . "GUID-B0EF0543-F792-4391-B54F-606F5685065C"))))
    *autolisp-reference-parts*))

(setq *autolisp-reference-parts*
  (cons
    '(("layerstate-has" .
          ((name . "layerstate-has")
           (title . "layerstate-has (AutoLISP)")
           (summary . "Checks if a layer state is present")
           (source-kind . "AutoLISP")
           (alphabetic-group . "L")
           (feature-groups . nil)
           (supported-platforms . "Windows and Mac OS")
           (signature . "(layerstate-has layerstatename)")
           (arguments . (("layerstatename" . "Type: String\nName of the layer state to be queried.")))
           (return-values . "Type: T or nil\nT if the name exists; otherwise nil.")
           (release-information . nil)
           (history . nil)
           (examples . "(layerstate-has \"myLayerState\")\nT")
           (url . "https://help.autodesk.com/cloudhelp/2023/ENU/AutoCAD-AutoLISP-Reference/files/GUID-0936B91C-7DE0-49DD-9BCD-FD097417E348.htm")
           (guid . "GUID-0936B91C-7DE0-49DD-9BCD-FD097417E348"))))
    *autolisp-reference-parts*))

(setq *autolisp-reference-parts*
  (cons
    '(("layerstate-import" .
          ((name . "layerstate-import")
           (title . "layerstate-import (AutoLISP)")
           (summary . "Imports a layer state from a specified file")
           (source-kind . "AutoLISP")
           (alphabetic-group . "L")
           (feature-groups . nil)
           (supported-platforms . "Windows and Mac OS")
           (signature . "(layerstate-import filename)")
           (arguments . (("filename" . "Type: String\nName of the file from which to import a layer state.")))
           (return-values . "Type: T or nil\nT if the import is successful; nil otherwise.")
           (release-information . nil)
           (history . nil)
           (examples . "Windows\n\n(layerstate-import \"c:\\\\mylayerstate.las\")\nT\n\nMac OS\n\n(layerstate-import \"/mylayerstate.las\")\nT")
           (url . "https://help.autodesk.com/cloudhelp/2023/ENU/AutoCAD-AutoLISP-Reference/files/GUID-E8B76E26-4E16-4AC6-B5E1-2CEA0C21EA1B.htm")
           (guid . "GUID-E8B76E26-4E16-4AC6-B5E1-2CEA0C21EA1B"))))
    *autolisp-reference-parts*))

(setq *autolisp-reference-parts*
  (cons
    '(("layerstate-importfromdb" .
          ((name . "layerstate-importfromdb")
           (title . "layerstate-importfromdb (AutoLISP)")
           (summary . "Imports a layer state from a specified drawing file")
           (source-kind . "AutoLISP")
           (alphabetic-group . "L")
           (feature-groups . nil)
           (supported-platforms . "Windows and Mac OS")
           (signature . "(layerstate-importfromdb layerstatename filename)")
           (arguments . (("layerstatename" . "Type: String\nName of the layer state to be imported.")
                           ("filename" . "Type: String\nName of the file from which to import a layer state.")))
           (return-values . "Type: T or nil\nT if the import is successful; nil otherwise.")
           (release-information . nil)
           (history . nil)
           (examples . "Windows\n\n(layerstate-importfromdb \"mylayerstate\" \"c:\\\\mydrawing.dwg\")\nT\n\nMac OS\n\n(layerstate-importfromdb \"mylayerstate\" \"/mydrawing.dwg\")\nT")
           (url . "https://help.autodesk.com/cloudhelp/2023/ENU/AutoCAD-AutoLISP-Reference/files/GUID-A41D1A72-5DD2-469B-B0AD-97233A98D5BB.htm")
           (guid . "GUID-A41D1A72-5DD2-469B-B0AD-97233A98D5BB"))))
    *autolisp-reference-parts*))

(setq *autolisp-reference-parts*
  (cons
    '(("layerstate-removelayers" .
          ((name . "layerstate-removelayers")
           (title . "layerstate-removelayers (AutoLISP)")
           (summary . "Removes a list of layers from a layer state")
           (source-kind . "AutoLISP")
           (alphabetic-group . "L")
           (feature-groups . nil)
           (supported-platforms . "Windows and Mac OS")
           (signature . "(layerstate-removelayers layerstatename (list layername layername layername ...))")
           (arguments . (("layerstatename" . "Type: String\nName of the layer state to be updated.")
                           ("layername" . "Type: String\nName of the layer state to be removed.")))
           (return-values . "Type: T or nil\nT if the remove is successful; otherwise nil.")
           (release-information . nil)
           (history . nil)
           (examples . "(layerstate-removelayers \"myLayerState\" (list \"Walls\" \"Elec1\" \"Foundation\" \"Plumbing\"))\nT")
           (url . "https://help.autodesk.com/cloudhelp/2023/ENU/AutoCAD-AutoLISP-Reference/files/GUID-5F9FFCEB-D7D6-4233-AC74-526B51C4FD42.htm")
           (guid . "GUID-5F9FFCEB-D7D6-4233-AC74-526B51C4FD42"))))
    *autolisp-reference-parts*))

(setq *autolisp-reference-parts*
  (cons
    '(("layerstate-rename" .
          ((name . "layerstate-rename")
           (title . "layerstate-rename (AutoLISP)")
           (summary . "Renames a layer state")
           (source-kind . "AutoLISP")
           (alphabetic-group . "L")
           (feature-groups . nil)
           (supported-platforms . "Windows and Mac OS")
           (signature . "(layerstate-rename oldlayerstatename newlayerstatename)")
           (arguments . (("oldlayerstatename" . "Type: String\nName of the layer state to be renamed.")
                           ("newlayerstatename" . "Type: String\nName of the layer state to be updated.")))
           (return-values . "Type: T or nil\nT if the rename is successful; otherwise nil.")
           (release-information . nil)
           (history . nil)
           (examples . "(layerstate-rename \"myLayerState\" \"myNewLayerState\")\nT")
           (url . "https://help.autodesk.com/cloudhelp/2023/ENU/AutoCAD-AutoLISP-Reference/files/GUID-843B8FC9-A1F5-48CE-B83D-98D747E85C83.htm")
           (guid . "GUID-843B8FC9-A1F5-48CE-B83D-98D747E85C83"))))
    *autolisp-reference-parts*))

(setq *autolisp-reference-parts*
  (cons
    '(("layerstate-restore" .
          ((name . "layerstate-restore")
           (title . "layerstate-restore (AutoLISP)")
           (summary . "Restores a layer state into the current drawing")
           (source-kind . "AutoLISP")
           (alphabetic-group . "L")
           (feature-groups . nil)
           (supported-platforms . "Windows and Mac OS")
           (signature . "(layerstate-restore layerstatename viewport [restoreflags])")
           (arguments . (("layerstatename" . "Type: String\nName of the layer to restore.")
                           ("viewport" . "Type: Ename (entity name)\nAn ename of the viewport to which layerstatename should be restored. If viewport is nil, the layer state is restored to model space.")
                           ("restoreflags" . "Type: Integer\nOptional numeric sum affecting how the layer state is restored.\n1 -- Turn off all layers not in the restored layer state\n2 -- Freeze all layers not in the restored layer state\n4 -- Restore the layer state properties as viewport overrides (requires viewport to be not a nil value).")))
           (return-values . "Type: List or nil\nnil if the layer state does not exist or contains no layers; otherwise, returns a list of layer names.")
           (release-information . nil)
           (history . nil)
           (examples . "(layerstate-restore \"myLayerState\" viewportId 5)\n(\"Layername1\" \"Layername2\")")
           (url . "https://help.autodesk.com/cloudhelp/2023/ENU/AutoCAD-AutoLISP-Reference/files/GUID-84C7195D-12C1-4282-B5EE-8B9D6DDB705A.htm")
           (guid . "GUID-84C7195D-12C1-4282-B5EE-8B9D6DDB705A"))))
    *autolisp-reference-parts*))

(setq *autolisp-reference-parts*
  (cons
    '(("layerstate-save" .
          ((name . "layerstate-save")
           (title . "layerstate-save (AutoLISP)")
           (summary . "Saves a layer state in the current drawing")
           (source-kind . "AutoLISP")
           (alphabetic-group . "L")
           (feature-groups . nil)
           (supported-platforms . "Windows and Mac OS")
           (signature . "(layerstate-save layerstatename mask viewport)")
           (arguments . (("layerstatename" . "Type: String\nName of the layer state to save.")
                           ("mask" . "Type: Integer\nNumeric sum designating which properties in the layer state are to be restored.\n1 -- Restore the saved On or Off value\n2 -- Restore the saved Frozen or Thawed value\n4 -- Restore the saved Lock value\n8 -- Restore the saved Plot or No Plot value\n16 -- Restore the saved VPVSDFLT value\n32 -- Restore the saved Color\n64 -- Restore the saved LineType\n128 -- Restore the saved LineWeight")
                           ("viewport" . "Type: Ename (entity name)\nAn ename of the viewport whose VPLAYER setting is to be captured. If nil, the layer state will be saved without VPLAYER settings.")))
           (return-values . "Type: T or nil\nT if the save is successful; otherwise nil.")
           (release-information . nil)
           (history . nil)
           (examples . "(layerstate-save \"myLayerState\" 21 viewportId)\nT\n\n(layerstate-save \"myLayerState\" nil nil)\nnil")
           (url . "https://help.autodesk.com/cloudhelp/2023/ENU/AutoCAD-AutoLISP-Reference/files/GUID-05B5EA5C-2E7F-47A5-9C6F-27902DB60F30.htm")
           (guid . "GUID-05B5EA5C-2E7F-47A5-9C6F-27902DB60F30"))))
    *autolisp-reference-parts*))

(setq *autolisp-reference-parts*
  (cons
    '(("layoutlist" .
          ((name . "layoutlist")
           (title . "layoutlist (AutoLISP)")
           (summary . "Returns a list of all paper space layouts in the current drawing")
           (source-kind . "AutoLISP")
           (alphabetic-group . "L")
           (feature-groups . ("Symbol Table and Dictionary-Handling"))
           (supported-platforms . "Windows and Mac OS")
           (signature . "(layoutlist)")
           (arguments . nil)
           (return-values . "Type: List\nA list of strings.")
           (release-information . nil)
           (history . nil)
           (examples . "(layoutlist)\n(\"Layout1\" \"Layout2\")")
           (url . "https://help.autodesk.com/cloudhelp/2023/ENU/AutoCAD-AutoLISP-Reference/files/GUID-AE3F338F-0B11-45B0-AB12-2C119203A977.htm")
           (guid . "GUID-AE3F338F-0B11-45B0-AB12-2C119203A977"))))
    *autolisp-reference-parts*))

(setq *autolisp-reference-parts*
  (cons
    '(("length" .
          ((name . "length")
           (title . "length (AutoLISP)")
           (summary . "Returns an integer indicating the number of elements in a list")
           (source-kind . "AutoLISP")
           (alphabetic-group . "L")
           (feature-groups . ("List Manipulation"))
           (supported-platforms . "Windows and Mac OS")
           (signature . "(length lst)")
           (arguments . (("lst" . "Type: List\nAn empty list or a list with one or more elements.")))
           (return-values . "Type: Integer\nA numeric value.")
           (release-information . nil)
           (history . nil)
           (examples . "(length '(a b c d))\n4\n\n(length '(a b (c d)))\n3\n\n(length '())\n0")
           (url . "https://help.autodesk.com/cloudhelp/2023/ENU/AutoCAD-AutoLISP-Reference/files/GUID-DD227383-1895-46B6-A83B-43000FCC1018.htm")
           (guid . "GUID-DD227383-1895-46B6-A83B-43000FCC1018"))))
    *autolisp-reference-parts*))

(setq *autolisp-reference-parts*
  (cons
    '(("list" .
          ((name . "list")
           (title . "list (AutoLISP)")
           (summary . "Takes any number of expressions and combines them into one list")
           (source-kind . "AutoLISP")
           (alphabetic-group . "L")
           (feature-groups . ("List Manipulation"))
           (supported-platforms . "Windows and Mac OS")
           (signature . "(list [expr ...])")
           (arguments . (("expr" . "Type: Integer, Real, String, List, Ename (entity name), T, or nil\nAn AutoLISP expression.")))
           (return-values . "Type: List or nil\nA list, unless no expressions are supplied, in which case list returns nil.")
           (release-information . nil)
           (history . nil)
           (examples . "(list 'a 'b 'c)\n(A B C)\n\n(list 'a '(b c) 'd)\n(A (B C) D)\n\n(list 3.9 6.7)\n(3.9 6.7)\n\nAs an alternative to using the list function, you can explicitly quote a list with the quote function if there are no variables or undefined items in the list. The single quote character (') is defined as the quote function.\n\n'(3.9 6.7) means the same as (list 3.9 6.7)\n\nThis can be useful for creating association lists and defining points.")
           (url . "https://help.autodesk.com/cloudhelp/2023/ENU/AutoCAD-AutoLISP-Reference/files/GUID-2BA66308-DE64-4BA6-8F57-6E3EC1A93141.htm")
           (guid . "GUID-2BA66308-DE64-4BA6-8F57-6E3EC1A93141"))))
    *autolisp-reference-parts*))

(setq *autolisp-reference-parts*
  (cons
    '(("listp" .
          ((name . "listp")
           (title . "listp (AutoLISP)")
           (summary . "Verifies that an item is a list")
           (source-kind . "AutoLISP")
           (alphabetic-group . "L")
           (feature-groups . ("List Manipulation"))
           (supported-platforms . "Windows and Mac OS")
           (signature . "(listp item)")
           (arguments . (("item" . "Type: Integer, Real, String, List, Ename (entity name), T, or nil\nAny atom, list, or expression.")))
           (return-values . "Type: T or nil\nT if item is a list; otherwise nil. Because nil is both an atom and a list, the listp function returns T when passed nil.")
           (release-information . nil)
           (history . nil)
           (examples . "(listp '(a b c))\nT\n\n(listp 'a)\nnil\n\n(listp 4.343)\nnil\n\n(listp nil)\nT\n\n(listp (setq v1 '(1 2 43)))\nT")
           (url . "https://help.autodesk.com/cloudhelp/2023/ENU/AutoCAD-AutoLISP-Reference/files/GUID-8755F083-D3BA-45F0-BBAF-D60D3A73240C.htm")
           (guid . "GUID-8755F083-D3BA-45F0-BBAF-D60D3A73240C"))))
    *autolisp-reference-parts*))

(setq *autolisp-reference-entry* nil)

(setq *autolisp-reference-value* "GUID-F3639BAA-FD70-487C-AEB5-9E6096EC0255")

(setq *autolisp-reference-entry* (cons (cons 'guid *autolisp-reference-value*) *autolisp-reference-entry*))

(setq *autolisp-reference-value* "https://help.autodesk.com/cloudhelp/2023/ENU/AutoCAD-AutoLISP-Reference/files/GUID-F3639BAA-FD70-487C-AEB5-9E6096EC0255.htm")

(setq *autolisp-reference-entry* (cons (cons 'url *autolisp-reference-value*) *autolisp-reference-entry*))

(setq *autolisp-reference-value* "For the following examples, assume that file /fred/test1.lsp contains the expressions\n\n(defun MY-FUNC1 (x)\n          ... function body ...\n)\n(defun MY-FUNC2 (x)\n          ... function body ...\n)\n\nand that no file named test2 with a .lsp, .fas, or .vlx extension exists:\n\n(load \"/fred/test1\")\nMY-FUNC2\n\n(load \"\\\\fred\\\\test1\")\nMY-FUNC2\n\n(load \"/fred/test1\" \"bad\")\nMY-FUNC2\n\n(load \"test2\" \"bad\")\n\"bad\"\n\n(load \"test2\")\n; error: LOAD failed: \"test2\"")

(setq *autolisp-reference-entry* (cons (cons 'examples *autolisp-reference-value*) *autolisp-reference-entry*))

(setq *autolisp-reference-value* "AutoCAD 2021\n- filename\n- argument previously accepted an ASCII text string, but now accepts a Unicode text string.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: String, Subroutine, or Error\nUnspecified, if successful. If load fails, it returns the value of onfailure; if onfailure is not defined, failure results in an error message.")

(setq *autolisp-reference-entry* (cons (cons 'return-values *autolisp-reference-value*) *autolisp-reference-entry*))

(setq *autolisp-reference-value* nil)

(setq *autolisp-reference-string* "Type: String\nA value returned if load fails.\nIf the onfailure argument is a valid AutoLISP function, it is evaluated. In most cases, the onfailure argument should be a string or an atom. This allows an AutoLISP application calling load to take alternative action upon failure.")

(setq *autolisp-reference-value* (cons (cons "onfailure" *autolisp-reference-string*) *autolisp-reference-value*))

(setq *autolisp-reference-string* "Type: String\nName of the AutoLISP file to load. If the filename argument does not specify a file extension, load adds an extension to the name when searching for a file to load. The function will try several extensions, if necessary, in the following order:\n- .vlx\n- .fas\n- .\n- lsp\nNote: VLX files are supported on Windows only.\nAs soon as load finds a match, it stops searching and loads the file.\nThe filename can include a directory prefix, as in c:/function/test1 (Windows) or /function/test1 (Mac OS). A forward slash (/) or two backslashes (\\\\) are valid directory delimiters. If you don't include a directory prefix in the filename string, load searches the AutoCAD library path for the specified file. If the file is found anywhere on this path, load then loads the file.")

(setq *autolisp-reference-value* (cons (cons "filename" *autolisp-reference-string*) *autolisp-reference-value*))

(setq *autolisp-reference-entry* (cons (cons 'arguments *autolisp-reference-value*) *autolisp-reference-entry*))

(setq *autolisp-reference-value* "(load filename [onfailure])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Application-Handling"))

(setq *autolisp-reference-entry* (cons (cons 'feature-groups *autolisp-reference-value*) *autolisp-reference-entry*))

(setq *autolisp-reference-value* "L")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Evaluates the AutoLISP expressions in a file")

(setq *autolisp-reference-entry* (cons (cons 'summary *autolisp-reference-value*) *autolisp-reference-entry*))

(setq *autolisp-reference-value* "load (AutoLISP)")

(setq *autolisp-reference-entry* (cons (cons 'title *autolisp-reference-value*) *autolisp-reference-entry*))

(setq *autolisp-reference-value* "load")

(setq *autolisp-reference-entry* (cons (cons 'name *autolisp-reference-value*) *autolisp-reference-entry*))

(setq *autolisp-reference-parts* (cons (list (cons "load" *autolisp-reference-entry*)) *autolisp-reference-parts*))

(setq *autolisp-reference-parts*
  (cons
    '(("load_dialog" .
          ((name . "load_dialog")
           (title . "load_dialog (AutoLISP/DCL)")
           (summary . "Loads a DCL file")
           (source-kind . "AutoLISP/DCL")
           (alphabetic-group . "L")
           (feature-groups . ("Dialog Box Opening and Closing Functions Reference (AutoLISP/DCL)"))
           (supported-platforms . "Windows and Mac OS")
           (signature . "(load_dialog dclfile)")
           (arguments . (("dclfile" . "Type: String\nDCL file to load. If the dclfile argument does not specify a file extension, .dcl is assumed.")))
           (return-values . "Type: Integer\nA positive integer value (dcl_id) if successful, or a negative integer if load_dialog cannot open the file. The dcl_id is used as a handle in subsequent new_dialog and unload_dialog calls.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-B5E4E72B-BD59-4E5E-8FBF-345DFC45A7EC.htm")
           (guid . "GUID-B5E4E72B-BD59-4E5E-8FBF-345DFC45A7EC"))))
    *autolisp-reference-parts*))

(setq *autolisp-reference-parts*
  (cons
    '(("log" .
          ((name . "log")
           (title . "log (AutoLISP)")
           (summary . "Returns the natural log of a number as a real number")
           (source-kind . "AutoLISP")
           (alphabetic-group . "L")
           (feature-groups . ("Arithmetic"))
           (supported-platforms . "Windows and Mac OS")
           (signature . "(log num)")
           (arguments . (("num" . "Type: Integer or Real\nA positive number.")))
           (return-values . "Type: Real\nA numeric value.")
           (release-information . nil)
           (history . nil)
           (examples . "(log 4.5)\n1.50408\n\n(log 1.22)\n0.198851")
           (url . "https://help.autodesk.com/cloudhelp/2023/ENU/AutoCAD-AutoLISP-Reference/files/GUID-4B1B6364-B1CB-4CE7-8C8F-706EA829780F.htm")
           (guid . "GUID-4B1B6364-B1CB-4CE7-8C8F-706EA829780F"))))
    *autolisp-reference-parts*))

(setq *autolisp-reference-parts*
  (cons
    '(("logand" .
          ((name . "logand")
           (title . "logand (AutoLISP)")
           (summary . "Returns the result of the logical bitwise AND of a list of integers")
           (source-kind . "AutoLISP")
           (alphabetic-group . "L")
           (feature-groups . ("Arithmetic"))
           (supported-platforms . "Windows and Mac OS")
           (signature . "(logand [int int ...])")
           (arguments . (("int" . "Type: Integer\nA numeric value.")))
           (return-values . "Type: Integer\nAn numeric value (0, if no arguments are supplied).")
           (release-information . nil)
           (history . nil)
           (examples . "(logand 7 15 3)\n3\n\n(logand 2 3 15)\n2\n\n(logand 8 3 4)\n0")
           (url . "https://help.autodesk.com/cloudhelp/2023/ENU/AutoCAD-AutoLISP-Reference/files/GUID-4E042C63-8BD7-4FED-B9E1-B5CE12D18273.htm")
           (guid . "GUID-4E042C63-8BD7-4FED-B9E1-B5CE12D18273"))))
    *autolisp-reference-parts*))

(setq *autolisp-reference-parts*
  (cons
    '(("logior" .
          ((name . "logior")
           (title . "logior (AutoLISP)")
           (summary . "Returns the result of the logical bitwise inclusive OR of a list of integers")
           (source-kind . "AutoLISP")
           (alphabetic-group . "L")
           (feature-groups . ("Arithmetic"))
           (supported-platforms . "Windows and Mac OS")
           (signature . "(logior [int int ...])")
           (arguments . (("int" . "Type: Integer\nA numeric value.")))
           (return-values . "Type: Integer\nA numeric value (0, if no arguments are supplied).")
           (release-information . nil)
           (history . nil)
           (examples . "(logior 1 2 4)\n7\n\n(logior 9 3)\n11")
           (url . "https://help.autodesk.com/cloudhelp/2023/ENU/AutoCAD-AutoLISP-Reference/files/GUID-A4BF3B68-4988-42F0-AFE6-BFD06D0DB159.htm")
           (guid . "GUID-A4BF3B68-4988-42F0-AFE6-BFD06D0DB159"))))
    *autolisp-reference-parts*))

(setq *autolisp-reference-parts*
  (cons
    '(("lsh" .
          ((name . "lsh")
           (title . "lsh (AutoLISP)")
           (summary . "Returns the logical bitwise shift of an integer by a specified number of bits")
           (source-kind . "AutoLISP")
           (alphabetic-group . "L")
           (feature-groups . ("Arithmetic"))
           (supported-platforms . "Windows and Mac OS")
           (signature . "(lsh int numbits)")
           (arguments . (("int" . "Type: Integer\nA numeric value.")
                           ("numbits" . "Type: Integer\nNumber of bits to shift int.\nIf numbits is positive, int is shifted to the left; if numbits is negative, int is shifted to the right. In either case, zero bits are shifted in, and the bits shifted out are discarded.\nIf numbits is not specified, no shift occurs.")))
           (return-values . "Type: Integer\nThe value of int after the bitwise shift. The returned value is positive if the significant bit (bit number 31) contains a 0 after the shift operation; otherwise it is negative. If no arguments are supplied, lsh returns 0.\nThe behavior is different from other languages (>> & << of C, C++, or Java) where more than 32 left shifts (of a 32 bit integer) result in 0. In right shift, the integer appears again on every 32 shifts.")
           (release-information . nil)
           (history . nil)
           (examples . "(lsh 2 1)\n4\n\n(lsh 2 -1)\n1\n\n(lsh 40 2)\n160")
           (url . "https://help.autodesk.com/cloudhelp/2023/ENU/AutoCAD-AutoLISP-Reference/files/GUID-3BC67533-3F4F-4C01-9053-CD82AA235AE8.htm")
           (guid . "GUID-3BC67533-3F4F-4C01-9053-CD82AA235AE8"))))
    *autolisp-reference-parts*))

(setq *autolisp-reference-parts*
  (cons
    '(("mapcar" .
          ((name . "mapcar")
           (title . "mapcar (AutoLISP)")
           (summary . "Returns a list that is the result of executing a function with a list (or lists) supplied as arguments to the function")
           (source-kind . "AutoLISP")
           (alphabetic-group . "M")
           (feature-groups . ("List Manipulation"))
           (supported-platforms . "Windows and Mac OS")
           (signature . "(mapcar function list1... listn)")
           (arguments . (("function" . "Type: Subroutine\nA function.")
                           ("list1... listn" . "Type: List\nOne or more lists. The number of lists must match the number of arguments required by function.")))
           (return-values . "Type: List\nA list.")
           (release-information . nil)
           (history . nil)
           (examples . "(setq a 10 b 20 c 30)\n30\n\n(mapcar '1+ (list a b c))\n(11 21 31)\n\nThis is equivalent to the following series of expressions, except that mapcar returns a list of the results:\n\n(1+ a)\n(1+ b)\n(1+ c)\n\nThe lambda function can specify an anonymous function to be performed by mapcar. This is useful when some of the function arguments are constant or are supplied by some other means. The following example demonstrates the use of lambda with mapcar:\n\n(mapcar '(lambda (x)\n          (+ x 3)\n          )\n         '(10 20 30)\n)\n(13 23 33)")
           (url . "https://help.autodesk.com/cloudhelp/2023/ENU/AutoCAD-AutoLISP-Reference/files/GUID-8802AE73-1A05-457E-8A51-09677C23E26E.htm")
           (guid . "GUID-8802AE73-1A05-457E-8A51-09677C23E26E"))))
    *autolisp-reference-parts*))

(setq *autolisp-reference-parts*
  (cons
    '(("max" .
          ((name . "max")
           (title . "max (AutoLISP)")
           (summary . "Returns the largest of the numbers given")
           (source-kind . "AutoLISP")
           (alphabetic-group . "M")
           (feature-groups . ("Arithmetic"))
           (supported-platforms . "Windows and Mac OS")
           (signature . "(max [number number ...])")
           (arguments . (("number" . "Type: Integer or Real\nA numeric value.")))
           (return-values . "Type: Integer or Real\nA number. If any of the arguments are real numbers, a real is returned; otherwise an integer is returned. If no argument is supplied, max returns 0.")
           (release-information . nil)
           (history . nil)
           (examples . "(max 4.07 -144)\n4.07\n\n(max -88 19 5 2)\n19\n\n(max 2.1 4 8)\n8.0")
           (url . "https://help.autodesk.com/cloudhelp/2023/ENU/AutoCAD-AutoLISP-Reference/files/GUID-057C56D3-8A15-406B-95CA-68DD859E64FB.htm")
           (guid . "GUID-057C56D3-8A15-406B-95CA-68DD859E64FB"))))
    *autolisp-reference-parts*))

(setq *autolisp-reference-parts*
  (cons
    '(("mem" .
          ((name . "mem")
           (title . "mem (AutoLISP)")
           (summary . "Displays the current state of the AutoLISP memory")
           (source-kind . "AutoLISP")
           (alphabetic-group . "M")
           (feature-groups . ("Memory Management"))
           (supported-platforms . "Windows and Mac OS")
           (signature . "(mem)")
           (arguments . nil)
           (return-values . "Type: nil\nAlways returns nil.")
           (release-information . nil)
           (history . nil)
           (examples . "(mem)\n; GC calls: 23; GC run time: 298 ms\nDynamic memory segments statistic:\nPgSz  Used  Free  FMCL  Segs  Type\n 512    79    48    48     1  lisp stacks\n 256  3706   423   142    16  bytecode area\n4096   320    10    10    22  CONS memory\n  32   769  1213  1089     1  ::new\n4096   168    12    10    12  DM Str\n4096   222     4     4    15  DMxx memory\n 128     4   507   507     1  bstack body\nSegment size: 65536, total used: 68, free: 0\nnil")
           (url . "https://help.autodesk.com/cloudhelp/2023/ENU/AutoCAD-AutoLISP-Reference/files/GUID-F4AEB953-2117-4BF2-8056-EA1384AC3FFF.htm")
           (guid . "GUID-F4AEB953-2117-4BF2-8056-EA1384AC3FFF"))))
    *autolisp-reference-parts*))

(setq *autolisp-reference-parts*
  (cons
    '(("member" .
          ((name . "member")
           (title . "member (AutoLISP)")
           (summary . "Searches a list for an occurrence of an expression and returns the remainder of the list, starting with the first occurrence of the expression")
           (source-kind . "AutoLISP")
           (alphabetic-group . "M")
           (feature-groups . ("List Manipulation"))
           (supported-platforms . "Windows and Mac OS")
           (signature . "(member expr lst)")
           (arguments . (("expr" . "Type: Integer, Real, String, List, Ename (entity name), T, or nil\nThe expression to be searched for.")
                           ("lst" . "Type: List\nThe list in which to search for expr.")))
           (return-values . "Type: List or nil\nA list; otherwise nil, if there is no occurrence of expr in lst.")
           (release-information . nil)
           (history . nil)
           (examples . "(member 'c '(a b c d e))\n(C D E)\n\n(member 'q '(a b c d e))\nnil")
           (url . "https://help.autodesk.com/cloudhelp/2023/ENU/AutoCAD-AutoLISP-Reference/files/GUID-A2B08751-D966-44F5-9B02-1AAC4DA6AF59.htm")
           (guid . "GUID-A2B08751-D966-44F5-9B02-1AAC4DA6AF59"))))
    *autolisp-reference-parts*))

(setq *autolisp-reference-entry* nil)

(setq *autolisp-reference-value* "GUID-20357966-71D4-4D55-881B-06AFDECD24DB")

(setq *autolisp-reference-entry* (cons (cons 'guid *autolisp-reference-value*) *autolisp-reference-entry*))

(setq *autolisp-reference-value* "https://help.autodesk.com/cloudhelp/2023/ENU/AutoCAD-AutoLISP-Reference/files/GUID-20357966-71D4-4D55-881B-06AFDECD24DB.htm")

(setq *autolisp-reference-entry* (cons (cons 'url *autolisp-reference-value*) *autolisp-reference-entry*))

(setq *autolisp-reference-value* "The following code displays the image tile menu MOREICONS:\n\n(menucmd \"I=moreicons\")       Loads the MOREICONS image tile menu\n(menucmd \"I=*\")               Displays the menu\n\nThe following code checks the status of the third menu item in the pull-down menu POP11. If the menu item is currently enabled, the menucmd function disables it.\n\n(setq s (menucmd \"P11.3=?\"))  Gets the status of the menu item\n(if (= s \"\")                  If the status is an empty string,\n  (menucmd \"P11.3=~\")         disable the menu item\n)\n\nThe previous code is not foolproof. In addition to being enabled or disabled, menu items can also receive marks. The code (menucmd \"P11.3=?\") could return \"!.\", indicating that the menu item is currently checked. This code would assume that the menu item is disabled and continue without disabling it. If the code included a call to the wcmatch function,")

(setq *autolisp-reference-value* (strcat *autolisp-reference-value* " it could check the status for an occurrence of the tilde (~) character and then take appropriate action.\n\nThe menucmd function also allows AutoLISP programs to take advantage of the DIESEL string expression language. Some things can be done more easily with DIESEL than with the equivalent AutoLISP code. The following code returns a string containing the current day and date:\n\n(menucmd \"M=$(edtime,$(getvar,date),DDDD\\\",\\\" D MONTH YYYY)\")\n\"Sunday, 16 July 1995\""))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: nil\nAlways returns nil.")

(setq *autolisp-reference-entry* (cons (cons 'return-values *autolisp-reference-value*) *autolisp-reference-entry*))

(setq *autolisp-reference-value* nil)

(setq *autolisp-reference-string* "Type: String\nMenu area and the value to assign to that menu area. The string argument has the following syntax:\n\"menu_area=value\"\nThe allowed values of menu_area, shown in the following list, are the same as they are in menu file submenu references.\nB1-B4 -- BUTTONS menus 1 through 4\nA1-A4 -- AUX menus 1 through 4\nP0-P16 -- Pull-down (POP) menus 0 through 16\nI -- Image tile menus\nS -- SCREEN menu (Obsolete)\nT1-T4 -- TABLET menus 1 through 4\nM -- DIESEL string expressions\nGmenugroup.nametag -- A menugroup and name tag.\nNote: Only Pull-down (POP) menus and DIESEL string expressions are supported on Mac OS.")

(setq *autolisp-reference-value* (cons (cons "str" *autolisp-reference-string*) *autolisp-reference-value*))

(setq *autolisp-reference-entry* (cons (cons 'arguments *autolisp-reference-value*) *autolisp-reference-entry*))

(setq *autolisp-reference-value* "(menucmd str)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Display Control"))

(setq *autolisp-reference-entry* (cons (cons 'feature-groups *autolisp-reference-value*) *autolisp-reference-entry*))

(setq *autolisp-reference-value* "M")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Issues menu commands, or sets and retrieves menu item status")

(setq *autolisp-reference-entry* (cons (cons 'summary *autolisp-reference-value*) *autolisp-reference-entry*))

(setq *autolisp-reference-value* "menucmd (AutoLISP)")

(setq *autolisp-reference-entry* (cons (cons 'title *autolisp-reference-value*) *autolisp-reference-entry*))

(setq *autolisp-reference-value* "menucmd")

(setq *autolisp-reference-entry* (cons (cons 'name *autolisp-reference-value*) *autolisp-reference-entry*))

(setq *autolisp-reference-parts* (cons (list (cons "menucmd" *autolisp-reference-entry*)) *autolisp-reference-parts*))

(setq *autolisp-reference-parts*
  (cons
    '(("menugroup" .
          ((name . "menugroup")
           (title . "menugroup (AutoLISP)")
           (summary . "Verifies that a menugroup is loaded")
           (source-kind . "AutoLISP")
           (alphabetic-group . "M")
           (feature-groups . ("Display Control"))
           (supported-platforms . "Windows only")
           (signature . "(menugroup groupname)")
           (arguments . (("groupname" . "Type: String\nMenu group name.")))
           (return-values . "Type: String or nil\nIf groupname matches a loaded menu group name, the function returns the groupname string; otherwise, it returns nil.")
           (release-information . nil)
           (history . nil)
           (examples . "N/A")
           (url . "https://help.autodesk.com/cloudhelp/2023/ENU/AutoCAD-AutoLISP-Reference/files/GUID-52FBC08B-F53F-4FC0-A5C5-ED3FA2BB8F4B.htm")
           (guid . "GUID-52FBC08B-F53F-4FC0-A5C5-ED3FA2BB8F4B"))))
    *autolisp-reference-parts*))

(setq *autolisp-reference-parts*
  (cons
    '(("min" .
          ((name . "min")
           (title . "min (AutoLISP)")
           (summary . "Returns the smallest of the numbers given")
           (source-kind . "AutoLISP")
           (alphabetic-group . "M")
           (feature-groups . ("Arithmetic"))
           (supported-platforms . "Windows and Mac OS")
           (signature . "(min [number number ...])")
           (arguments . (("number" . "Type: Integer or Real\nA numeric value.")))
           (return-values . "Type: Integer or Real\nA numeric value. If any number argument is a real, a real is returned; otherwise, an integer is returned. If no argument is supplied, min returns 0.")
           (release-information . nil)
           (history . nil)
           (examples . "(min 683 -10.0)\n-10.0\n\n(min 73 2 48 5)\n2\n\n(min 73.0 2 48 5)\n2.0\n\n(min 2 4 6.7)\n2.0")
           (url . "https://help.autodesk.com/cloudhelp/2023/ENU/AutoCAD-AutoLISP-Reference/files/GUID-F401AD55-57B2-4B1A-9704-D7D8D45AE465.htm")
           (guid . "GUID-F401AD55-57B2-4B1A-9704-D7D8D45AE465"))))
    *autolisp-reference-parts*))

(setq *autolisp-reference-parts*
  (cons
    '(("minusp" .
          ((name . "minusp")
           (title . "minusp (AutoLISP)")
           (summary . "Verifies that a number is negative")
           (source-kind . "AutoLISP")
           (alphabetic-group . "M")
           (feature-groups . ("Arithmetic"))
           (supported-platforms . "Windows and Mac OS")
           (signature . "(minusp num)")
           (arguments . (("num" . "Type: Integer or Real\nA numeric value.")))
           (return-values . "Type: T or nil\nT if number is negative; otherwise nil.")
           (release-information . nil)
           (history . nil)
           (examples . "(minusp -1)\nT\n\n(minusp -4.293)\nT\n\n(minusp 830.2)\nnil")
           (url . "https://help.autodesk.com/cloudhelp/2023/ENU/AutoCAD-AutoLISP-Reference/files/GUID-44E8AFFA-B322-4B26-B436-D83FDAB5CCDB.htm")
           (guid . "GUID-44E8AFFA-B322-4B26-B436-D83FDAB5CCDB"))))
    *autolisp-reference-parts*))

(setq *autolisp-reference-parts*
  (cons
    '(("mode_tile" .
          ((name . "mode_tile")
           (title . "mode_tile (AutoLISP/DCL)")
           (summary . "Sets the mode of a dialog box tile")
           (source-kind . "AutoLISP/DCL")
           (alphabetic-group . "M")
           (feature-groups . ("Tile- and Attribute-Handling Functions Reference (AutoLISP/DCL)"))
           (supported-platforms . "Windows and Mac OS")
           (signature . "(mode_tile key mode)")
           (arguments . (("key" . "Type: String\nValue that specifies a tile. This argument is case-sensitive.")
                           ("mode" . "Type: Integer\nA numeric value that can be one of the following:\n0 -- Enable tile\n1 -- Disable tile\n2 -- Set focus to tile\n3 -- Select edit box contents\n4 -- Flip image highlighting on or off")))
           (return-values . "Type: nil\nAlways returns nil.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-23ACCF72-9C6F-45C0-A889-9307CC1210C2.htm")
           (guid . "GUID-23ACCF72-9C6F-45C0-A889-9307CC1210C2"))))
    *autolisp-reference-parts*))

(setq *autolisp-reference-parts*
  (cons
    '(("namedobjdict" .
          ((name . "namedobjdict")
           (title . "namedobjdict (AutoLISP)")
           (summary . "Returns the entity name of the current drawing's named object dictionary, which is the root of all nongraphical objects in the drawing")
           (source-kind . "AutoLISP")
           (alphabetic-group . "N")
           (feature-groups . ("Symbol Table and Dictionary-Handling"))
           (supported-platforms . "Windows and Mac OS")
           (signature . "(namedobjdict)")
           (arguments . nil)
           (return-values . "Type: Ename (entity name)\nAlways returns an ename.")
           (release-information . nil)
           (history . nil)
           (examples . "(namedobjdict)\n<Entity name: 7ffffb038c0>")
           (url . "https://help.autodesk.com/cloudhelp/2023/ENU/AutoCAD-AutoLISP-Reference/files/GUID-A1E43B30-EF8C-452E-97F5-8AC201E310EE.htm")
           (guid . "GUID-A1E43B30-EF8C-452E-97F5-8AC201E310EE"))))
    *autolisp-reference-parts*))

(setq *autolisp-reference-entry* nil)

(setq *autolisp-reference-value* "GUID-A7AC0917-66CE-4BAA-BBAF-D49F8ADB26B1")

(setq *autolisp-reference-entry* (cons (cons 'guid *autolisp-reference-value*) *autolisp-reference-entry*))

(setq *autolisp-reference-value* "https://help.autodesk.com/cloudhelp/2023/ENU/AutoCAD-AutoLISP-Reference/files/GUID-A7AC0917-66CE-4BAA-BBAF-D49F8ADB26B1.htm")

(setq *autolisp-reference-entry* (cons (cons 'url *autolisp-reference-value*) *autolisp-reference-entry*))

(setq *autolisp-reference-value* "Draw a 3D polyline with multiple line segments; then load and run the following function and select different segments of the line. Pick off the line and then pick the same segments again to see the subentity handle. Try it with a lightweight polyline to see the difference.\n\n(defun c:subent ()\n  (while\n     (setq Ent (entsel \"\\nPick an entity: \"))\n     (print (strcat \"Entity handle is: \"\n          (cdr (assoc 5 (entget (car Ent))))))\n   )\n   (while\n      (setq Ent (nentsel \"\\nPick an entity or subEntity: \"))\n      (print (strcat \"Entity or subEntity handle is:  \"\n          (cdr (assoc 5 (entget (car Ent))))))\n   )\n  (prompt \"\\nDone.\")\n (princ)\n)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Ename (entity name)\nWhen the selected object is not complex (that is, not a 3D polyline or block), nentsel returns the same information as entsel. However, if the selected object is a 3D polyline, nentsel returns a list containing the name of the subentity (vertex) and the pick point. This is similar to the list returned by entsel, except that the name of the selected vertex is returned instead of the polyline header. The nentsel function always returns the starting vertex of the selected 3D polyline segment. Picking the third segment of the polyline, for example, returns the third vertex. The Seqend subentity is never returned by nentsel for a 3D polyline.\nNote: A lightweight polyline (lwpolyline entity) is defined in the drawing database as a single entity; it does not contain subentities.\nSelecting an attribute within a block reference returns the name of the attribute and th")

(setq *autolisp-reference-value* (strcat *autolisp-reference-value* "e pick point. When the selected object is a component of a block reference other than an attribute, nentsel returns a list containing four elements.\nThe first element of the list returned from picking an object within a block is the selected entity's name.\nThe second element is a list containing the coordinates of the point used to pick the object.\nThe third element is called the Model to World Transformation Matrix. It is a list consisting of four sublists, each of which contains a set of coordinates. This matrix can be used to transform the entity definition data points from an internal coordinate system called the Model Coordinate System (MCS), to the World Coordinate System (WCS). The insertion point of the block that contains the selected entity defines the origin of the MCS. The orientation of the UCS when the block is created determines the direction of the MCS axes.\nNote: nen"))

(setq *autolisp-reference-value* (strcat *autolisp-reference-value* "tsel is the only AutoLISP function that uses a matrix of this type; the nentselp function returns a matrix similar to those used by other AutoLISP and ObjectARX functions.\nThe fourth element is a list containing the entity name of the block that contains the selected object. If the selected object is in a nested block (a block within a block), the list also contains the entity names of all blocks in which the selected object is nested, starting with the innermost block and continuing outward until the name of the block that was inserted in the drawing is reported."))

(setq *autolisp-reference-entry* (cons (cons 'return-values *autolisp-reference-value*) *autolisp-reference-entry*))

(setq *autolisp-reference-value* nil)

(setq *autolisp-reference-string* "Type: String\nMessage to be displayed as a prompt. If the msg argument is omitted, the Select Object prompt is issued.")

(setq *autolisp-reference-value* (cons (cons "msg" *autolisp-reference-string*) *autolisp-reference-value*))

(setq *autolisp-reference-entry* (cons (cons 'arguments *autolisp-reference-value*) *autolisp-reference-entry*))

(setq *autolisp-reference-value* "(nentsel [msg])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("User Input"))

(setq *autolisp-reference-entry* (cons (cons 'feature-groups *autolisp-reference-value*) *autolisp-reference-entry*))

(setq *autolisp-reference-value* "N")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Prompts the user to select an object (entity) by specifying a point, and provides access to the definition data contained within a complex object")

(setq *autolisp-reference-entry* (cons (cons 'summary *autolisp-reference-value*) *autolisp-reference-entry*))

(setq *autolisp-reference-value* "nentsel (AutoLISP)")

(setq *autolisp-reference-entry* (cons (cons 'title *autolisp-reference-value*) *autolisp-reference-entry*))

(setq *autolisp-reference-value* "nentsel")

(setq *autolisp-reference-entry* (cons (cons 'name *autolisp-reference-value*) *autolisp-reference-entry*))

(setq *autolisp-reference-parts* (cons (list (cons "nentsel" *autolisp-reference-entry*)) *autolisp-reference-parts*))

(setq *autolisp-reference-parts*
  (cons
    '(("nentselp" .
          ((name . "nentselp")
           (title . "nentselp (AutoLISP)")
           (summary . "Provides similar functionality to that of the nentsel function without the need for user input")
           (source-kind . "AutoLISP")
           (alphabetic-group . "N")
           (feature-groups . ("User Input"))
           (supported-platforms . "Windows and Mac OS")
           (signature . "(nentselp [msg] [pt])")
           (arguments . (("msg" . "Type: String\nMessage to be displayed as a prompt. If the msg argument is omitted, the Select object prompt is issued.")
                           ("pt" . "Type: List\nA selection point. This allows object selection without user input.")))
           (return-values . "Type: List or nil\nThe nentselp function returns a 4×4 transformation matrix, defined as follows:\nThe first three columns of the matrix specify scaling and rotation. The fourth column is a translation vector.\nThe functions that use a matrix of this type treat a point as a column vector of dimension 4. The point is expressed in homogeneous coordinates, where the fourth element of the point vector is a scale factor that is normally set to 1.0. The final row of the matrix, the vector [M 30 M 31 M 32 M 33 ], has the nominal value of [0 0 0 1]; it is currently ignored by the functions that use this matrix format.")
           (release-information . nil)
           (history . nil)
           (examples . "N/A")
           (url . "https://help.autodesk.com/cloudhelp/2023/ENU/AutoCAD-AutoLISP-Reference/files/GUID-5CE182FE-6455-4C62-B953-B1CA441455C1.htm")
           (guid . "GUID-5CE182FE-6455-4C62-B953-B1CA441455C1"))))
    *autolisp-reference-parts*))

(setq *autolisp-reference-entry* nil)

(setq *autolisp-reference-value* "GUID-C971FCB7-F552-455D-AC2B-4DCD8A0ADCC1")

(setq *autolisp-reference-entry* (cons (cons 'guid *autolisp-reference-value*) *autolisp-reference-entry*))

(setq *autolisp-reference-value* "https://help.autodesk.com/cloudhelp/2023/ENU/AutoCAD-AutoLISP-Reference/files/GUID-C971FCB7-F552-455D-AC2B-4DCD8A0ADCC1.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* "Releases:\n- AutoCAD R12 and later on Windows\n- AutoCAD 2021 and later on Mac OS")

(setq *autolisp-reference-entry* (cons (cons 'release-information *autolisp-reference-value*) *autolisp-reference-entry*))

(setq *autolisp-reference-value* "Type: T or nil\nT, if successful; otherwise nil.")

(setq *autolisp-reference-entry* (cons (cons 'return-values *autolisp-reference-value*) *autolisp-reference-entry*))

(setq *autolisp-reference-value* nil)

(setq *autolisp-reference-string* "Type: List\nA 2D point that specifies the X,Y location of the dialog box on the screen. The point specifies the upper-left corner of the dialog box. If you pass the point as '(-1 -1), the dialog box is opened in the default position (the center of the AutoCAD drawing area).")

(setq *autolisp-reference-value* (cons (cons "screen-pt" *autolisp-reference-string*) *autolisp-reference-value*))

(setq *autolisp-reference-string* "Type: String\nAutoLISP expression to use as the default action. If you don't want to define a default action, specify an empty string (\"\"). The action argument is required if you specify screen-pt.\nThe default action is evaluated when the user picks an active tile that doesn't have an action or callback explicitly assigned to it by action_tile or in DCL.")

(setq *autolisp-reference-value* (cons (cons "action" *autolisp-reference-string*) *autolisp-reference-value*))

(setq *autolisp-reference-string* "Type: Integer\nThe DCL file identifier obtained by load_dialog.")

(setq *autolisp-reference-value* (cons (cons "dcl_id" *autolisp-reference-string*) *autolisp-reference-value*))

(setq *autolisp-reference-string* "Type: String\nDialog box.")

(setq *autolisp-reference-value* (cons (cons "dlgname" *autolisp-reference-string*) *autolisp-reference-value*))

(setq *autolisp-reference-entry* (cons (cons 'arguments *autolisp-reference-value*) *autolisp-reference-entry*))

(setq *autolisp-reference-value* "(new_dialog dlgname dcl_id [action [screen-pt]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Dialog Box Opening and Closing Functions Reference (AutoLISP/DCL)"))

(setq *autolisp-reference-entry* (cons (cons 'feature-groups *autolisp-reference-value*) *autolisp-reference-entry*))

(setq *autolisp-reference-value* "N")

(setq *autolisp-reference-entry* (cons (cons 'alphabetic-group *autolisp-reference-value*) *autolisp-reference-entry*))

(setq *autolisp-reference-value* "AutoLISP/DCL")

(setq *autolisp-reference-entry* (cons (cons 'source-kind *autolisp-reference-value*) *autolisp-reference-entry*))

(setq *autolisp-reference-value* "Begins a new dialog box and displays it, and can also specify a default action")

(setq *autolisp-reference-entry* (cons (cons 'summary *autolisp-reference-value*) *autolisp-reference-entry*))

(setq *autolisp-reference-value* "new_dialog (AutoLISP/DCL)")

(setq *autolisp-reference-entry* (cons (cons 'title *autolisp-reference-value*) *autolisp-reference-entry*))

(setq *autolisp-reference-value* "new_dialog")

(setq *autolisp-reference-entry* (cons (cons 'name *autolisp-reference-value*) *autolisp-reference-entry*))

(setq *autolisp-reference-parts* (cons (list (cons "new_dialog" *autolisp-reference-entry*)) *autolisp-reference-parts*))

(setq *autolisp-reference-parts*
  (cons
    '(("not" .
          ((name . "not")
           (title . "not (AutoLISP)")
           (summary . "Verifies that an item evaluates to nil")
           (source-kind . "AutoLISP")
           (alphabetic-group . "N")
           (feature-groups . ("Symbol-Handling"))
           (supported-platforms . "Windows and Mac OS")
           (signature . "(not item)")
           (arguments . (("item" . "Type: Integer, Real, String, List, Subroutine, Ename (entity name), T, or nil\nAn AutoLISP expression.")))
           (return-values . "Type: T or nil\nT if item evaluates to nil; otherwise nil.")
           (release-information . nil)
           (history . nil)
           (examples . "(setq a 123 b \"string\" c nil)\nnil\n\n(not a)\nnil\n\n(not b)\nnil\n\n(not c)\nT\n\n(not '())\nT")
           (url . "https://help.autodesk.com/cloudhelp/2023/ENU/AutoCAD-AutoLISP-Reference/files/GUID-991AD6A0-61AA-45C9-8C27-CADF9F36BE71.htm")
           (guid . "GUID-991AD6A0-61AA-45C9-8C27-CADF9F36BE71"))))
    *autolisp-reference-parts*))

(setq *autolisp-reference-parts*
  (cons
    '(("nth" .
          ((name . "nth")
           (title . "nth (AutoLISP)")
           (summary . "Returns the nth element of a list")
           (source-kind . "AutoLISP")
           (alphabetic-group . "N")
           (feature-groups . ("List Manipulation"))
           (supported-platforms . "Windows and Mac OS")
           (signature . "(nth n lst)")
           (arguments . (("n" . "Type: Integer\nThe number of the element to return from the list (zero is the first element).")
                           ("lst" . "Type: List\nThe list with one or more elements.")))
           (return-values . "Type: Integer, Real, String, List, Ename (entity name), T, or nil\nThe nth element of lst. If n is greater than the highest element number of lst, nth returns nil.")
           (release-information . nil)
           (history . nil)
           (examples . "(nth 3 '(a b c d e))\nD\n\n(nth 0 '(a b c d e))\nA\n\n(nth 5 '(a b c d e))\nnil")
           (url . "https://help.autodesk.com/cloudhelp/2023/ENU/AutoCAD-AutoLISP-Reference/files/GUID-0330FE17-6E15-4E34-BB50-E9040EABDADB.htm")
           (guid . "GUID-0330FE17-6E15-4E34-BB50-E9040EABDADB"))))
    *autolisp-reference-parts*))

(setq *autolisp-reference-parts*
  (cons
    '(("null" .
          ((name . "null")
           (title . "null (AutoLISP)")
           (summary . "Verifies that an item is bound to nil")
           (source-kind . "AutoLISP")
           (alphabetic-group . "N")
           (feature-groups . ("Symbol-Handling"))
           (supported-platforms . "Windows and Mac OS")
           (signature . "(null item)")
           (arguments . (("item" . "Type: Integer, Real, String, List, Ename (entity name), T, or nil\nAn AutoLISP expression.")))
           (return-values . "Type: T or nil\nT if item evaluates to nil; otherwise nil.")
           (release-information . nil)
           (history . nil)
           (examples . "(setq a 123 b \"string\" c nil)\nnil\n\n(null a)\nnil\n\n(null b)\nnil\n\n(null c)\nT\n\n(null '())\nT")
           (url . "https://help.autodesk.com/cloudhelp/2023/ENU/AutoCAD-AutoLISP-Reference/files/GUID-2CA2E5F1-297F-4ECA-9500-5FFCD4877126.htm")
           (guid . "GUID-2CA2E5F1-297F-4ECA-9500-5FFCD4877126"))))
    *autolisp-reference-parts*))

(setq *autolisp-reference-parts*
  (cons
    '(("numberp" .
          ((name . "numberp")
           (title . "numberp (AutoLISP)")
           (summary . "Verifies that an item is a real number or an integer")
           (source-kind . "AutoLISP")
           (alphabetic-group . "N")
           (feature-groups . ("Symbol-Handling"))
           (supported-platforms . "Windows and Mac OS")
           (signature . "(numberp item)")
           (arguments . (("item" . "Type: Integer, Real, String, List, Subroutine, Ename (entity name), T, or nil\nAn AutoLISP expression.")))
           (return-values . "Type: T or nil\nT if item evaluates to a real or an integer; otherwise nil.")
           (release-information . nil)
           (history . nil)
           (examples . "(setq a 123 b 'a)\nA\n\n(numberp 4)\nT\n\n(numberp 3.8348)\nT\n\n(numberp \"Howdy\")\nnil\n\n(numberp a)\nT\n\n(numberp b)\nnil\n\n(numberp (eval b))\nT")
           (url . "https://help.autodesk.com/cloudhelp/2023/ENU/AutoCAD-AutoLISP-Reference/files/GUID-1E5B591C-F60B-43CB-8CD8-E729D72B12FC.htm")
           (guid . "GUID-1E5B591C-F60B-43CB-8CD8-E729D72B12FC"))))
    *autolisp-reference-parts*))

(setq *autolisp-reference-entry* nil)

(setq *autolisp-reference-value* "GUID-089A323F-21FF-4337-99A9-375758E23BA4")

(setq *autolisp-reference-entry* (cons (cons 'guid *autolisp-reference-value*) *autolisp-reference-entry*))

(setq *autolisp-reference-value* "https://help.autodesk.com/cloudhelp/2023/ENU/AutoCAD-AutoLISP-Reference/files/GUID-089A323F-21FF-4337-99A9-375758E23BA4.htm")

(setq *autolisp-reference-entry* (cons (cons 'url *autolisp-reference-value*) *autolisp-reference-entry*))

(setq *autolisp-reference-value* "Windows\n\nOpen an existing file:\n(setq a (open \"c:/datafiles/filelist.txt\" \"r\"))\n#<file \"c:/datafiles/filelist.txt\">\nThe following examples issue open against files that do not exist:\n(setq f (open \"c:\\\\my documents\\\\new.tst\" \"w\"))\n#<file \"c:\\\\my documents\\\\new.tst\">\n\n(setq f (open \"nosuch.fil\" \"r\"))\nnil\n\n(setq f (open \"logfile\" \"a\"))\n#<file \"logfile\">\n\nMac OS\n\nOpen an existing file:\n(setq a (open \"/datafiles/filelist.txt\" \"r\"))\n#<file \"/datafiles/filelist.txt\">\nThe following examples issue open against files that do not exist:\n(setq f (open \"/my documents/new.tst\" \"w\"))\n#<file \"/my documents/new.tst\">\n\n(setq f (open \"nosuch.fil\" \"r\"))\nnil\n\n(setq f (open \"logfile\" \"a\"))\n#<file \"logfile\">")

(setq *autolisp-reference-entry* (cons (cons 'examples *autolisp-reference-value*) *autolisp-reference-entry*))

(setq *autolisp-reference-value* "AutoCAD 2021\n- filename\n- argument previously accepted an ASCII text string, but now accepts a Unicode text string.\n- encoding\n- argument is newly added.\n- LISPSYS system variable controls which AutoLISP engine is used and the behavior of the function.\n-   - 0 - ASCII character support and no\n-   - encoding\n-   - argument (legacy behavior)\n-   - 1 or 2 - Unicode character support\n- Note: After the value of the LISPSYS system variable has been changed, AutoCAD must be restarted for the change to take affect.\nAutoCAD 2000\n- mode\n- argument previously only accepted a lowercase value.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: File or nil\nIf successful, open returns a file descriptor that can be used by the other I/O functions. If mode \"r\" is specified and filename does not exist, open returns nil.")

(setq *autolisp-reference-entry* (cons (cons 'return-values *autolisp-reference-value*) *autolisp-reference-entry*))

(setq *autolisp-reference-value* nil)

(setq *autolisp-reference-string* "Type: String\nIndicates the character encoding to use when reading the file. When a value isn't provided for the argument, the file is assumed to contain multibyte character set (MBCS) which is the legacy behavior.\nUse one of the following values to specify a different character encoding:\nutf8 UTF-8\nutf8-bom UTF-8 with Byte Order Marks")

(setq *autolisp-reference-value* (cons (cons "encoding" *autolisp-reference-string*) *autolisp-reference-value*))

(setq *autolisp-reference-string* "Type: String\nIndicates whether the file is open for reading, writing, or appending. Specify a string containing one of the following letters:\nr Open for reading.\nw Open for writing. If filename does not exist, a new file is created and opened. If filename already exists, its existing data is overwritten. Data passed to an open file is not actually written until the file is closed with the close function.\na Open for appending. If filename does not exist, a new file is created and opened. If filename already exists, it is opened and the pointer is positioned at the end of the existing data, so new data you write to the file is appended to the existing data.\nThe mode argument can be uppercase or lowercase.\nNote: Prior to AutoCAD 2000, mode had to be specified in lowercase.")

(setq *autolisp-reference-value* (cons (cons "mode" *autolisp-reference-string*) *autolisp-reference-value*))

(setq *autolisp-reference-string* "Type: String\nName and extension of the file to be opened. If you do not specify the full path name of the file, open assumes you are referring to the AutoCAD default drawing directory.")

(setq *autolisp-reference-value* (cons (cons "filename" *autolisp-reference-string*) *autolisp-reference-value*))

(setq *autolisp-reference-entry* (cons (cons 'arguments *autolisp-reference-value*) *autolisp-reference-entry*))

(setq *autolisp-reference-value* "(open filename mode [encoding])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "O")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Opens a file for access by the AutoLISP I/O functions")

(setq *autolisp-reference-entry* (cons (cons 'summary *autolisp-reference-value*) *autolisp-reference-entry*))

(setq *autolisp-reference-value* "open (AutoLISP)")

(setq *autolisp-reference-entry* (cons (cons 'title *autolisp-reference-value*) *autolisp-reference-entry*))

(setq *autolisp-reference-value* "open")

(setq *autolisp-reference-entry* (cons (cons 'name *autolisp-reference-value*) *autolisp-reference-entry*))

(setq *autolisp-reference-parts* (cons (list (cons "open" *autolisp-reference-entry*)) *autolisp-reference-parts*))

(setq *autolisp-reference-parts*
  (cons
    '(("or" .
          ((name . "or")
           (title . "or (AutoLISP)")
           (summary . "Returns the logical OR of a list of expressions")
           (source-kind . "AutoLISP")
           (alphabetic-group . "O")
           (feature-groups . ("Equality and Conditional"))
           (supported-platforms . "Windows and Mac OS")
           (signature . "(or [expr ...])")
           (arguments . (("expr" . "Type: Integer, Real, String, List, Subroutine, Ename (entity name), T, or nil\nThe expressions to be evaluated.")))
           (return-values . "Type: T or nil\nT, if a non-nil expression is found; otherwise nil, if all of the expressions are nil or no arguments are supplied.\nNote that or accepts an atom as an argument and returns T if one is supplied.")
           (release-information . nil)
           (history . nil)
           (examples . "(or nil 45 '())\nT\n\n(or nil '())\nnil")
           (url . "https://help.autodesk.com/cloudhelp/2023/ENU/AutoCAD-AutoLISP-Reference/files/GUID-64ECF4D5-0714-45FD-8E27-284E9D2FC8B2.htm")
           (guid . "GUID-64ECF4D5-0714-45FD-8E27-284E9D2FC8B2"))))
    *autolisp-reference-parts*))

(setq *autolisp-reference-parts*
  (cons
    '(("osnap" .
          ((name . "osnap")
           (title . "osnap (AutoLISP)")
           (summary . "Returns a 3D point that is the result of applying an Object Snap mode to a specified point")
           (source-kind . "AutoLISP")
           (alphabetic-group . "O")
           (feature-groups . ("Geometric"))
           (supported-platforms . "Windows and Mac OS")
           (signature . "(osnap pt mode)")
           (arguments . (("pt" . "Type: List\nA point.")
                           ("mode" . "Type: String\nOne or more valid Object Snap identifiers, such as mid, cen, and so on, separated by commas.")))
           (return-values . "Type: List or nil\nA point; otherwise nil, if the pick did not return an object (for example, if there is no geometry under the pick aperture, or if the geometry is not applicable to the selected object snap mode). The point returned by osnap depends on the current 3D view, the AutoCAD entity around pt, and the setting of the AutoCAD APERTURE system variable.")
           (release-information . nil)
           (history . nil)
           (examples . "(setq pt1 (getpoint))\n(11.8637 3.28269 0.0)\n\n(setq pt2 (osnap pt1 \"_end,_int\"))\n(12.1424 3.42181 0.0)")
           (url . "https://help.autodesk.com/cloudhelp/2023/ENU/AutoCAD-AutoLISP-Reference/files/GUID-33498AA8-EDC0-45A3-9603-47A3F3510924.htm")
           (guid . "GUID-33498AA8-EDC0-45A3-9603-47A3F3510924"))))
    *autolisp-reference-parts*))

(setq *autolisp-reference-parts*
  (cons
    '(("polar" .
          ((name . "polar")
           (title . "polar (AutoLISP)")
           (summary . "Returns the UCS 3D point at a specified angle and distance from a point")
           (source-kind . "AutoLISP")
           (alphabetic-group . "P")
           (feature-groups . ("Geometric"))
           (supported-platforms . "Windows and Mac OS")
           (signature . "(polar pt ang dist)")
           (arguments . (("pt" . "Type: List\nA 2D or 3D point.")
                           ("ang" . "Type: Integer or Real\nAn angle expressed in radians relative to the world X axis. Angles increase in the counterclockwise direction, independent of the current construction plane.")
                           ("dist" . "Type: Integer or Real\nDistance from the specified pt.")))
           (return-values . "Type: List\nA 2D or 3D point, depending on the type of point specified by pt.")
           (release-information . nil)
           (history . nil)
           (examples . "Supplying a 3D point to polar:\n\n(polar '(1 1 3.5) 0.785398 1.414214)\n(2.0 2.0 3.5)\n\nSupplying a 2D point to polar :\n\n(polar '(1 1) 0.785398 1.414214)\n(2.0 2.0)")
           (url . "https://help.autodesk.com/cloudhelp/2023/ENU/AutoCAD-AutoLISP-Reference/files/GUID-6A84BFD3-8788-45B1-AB52-5E83F0C5286E.htm")
           (guid . "GUID-6A84BFD3-8788-45B1-AB52-5E83F0C5286E"))))
    *autolisp-reference-parts*))

(setq *autolisp-reference-entry* nil)

(setq *autolisp-reference-value* "GUID-BF4CEE45-BB6F-443B-A588-A40D9BCE378F")

(setq *autolisp-reference-entry* (cons (cons 'guid *autolisp-reference-value*) *autolisp-reference-entry*))

(setq *autolisp-reference-value* "https://help.autodesk.com/cloudhelp/2023/ENU/AutoCAD-AutoLISP-Reference/files/GUID-BF4CEE45-BB6F-443B-A588-A40D9BCE378F.htm")

(setq *autolisp-reference-entry* (cons (cons 'url *autolisp-reference-value*) *autolisp-reference-entry*))

(setq *autolisp-reference-value* "(setq a 123 b '(a))\n(A)\n\n(prin1 'a)\nAA\n\nThe previous command printed A and returned A.\n\n(prin1 a)\n123123\n\nThe previous command printed 123 and returned 123.\n\n(prin1 b)\n(A)(A)\n\nThe previous command printed (A) and returned (A).\n\nEach preceding example is displayed on the screen because no file-desc was specified. Assuming that f is a valid file descriptor for a file opened for writing, the following function call writes a string to that file and returns the string:\n\n(prin1 \"Hello\" f)\n\"Hello\"")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, List, Symbol, File, Ename (entity name), T, or nil\nThe value of the evaluated expr. If called with no arguments, prin1 returns a null symbol.\nUsed as the last expression in a function, prin1 without arguments prints a blank line when the function completes, allowing the function to exit “quietly.”")

(setq *autolisp-reference-entry* (cons (cons 'return-values *autolisp-reference-value*) *autolisp-reference-entry*))

(setq *autolisp-reference-value* nil)

(setq *autolisp-reference-string* "Type: File or nil\nA file descriptor for a file opened for writing.")

(setq *autolisp-reference-value* (cons (cons "file-desc" *autolisp-reference-string*) *autolisp-reference-value*))

(setq *autolisp-reference-string* "Type: Integer, Real, String, List, Symbol, File, Ename (entity name), T, or nil\nA string or AutoLISP expression. Only the specified expr is printed; no newline or space is included.")

(setq *autolisp-reference-value* (cons (cons "expr" *autolisp-reference-string*) *autolisp-reference-value*))

(setq *autolisp-reference-entry* (cons (cons 'arguments *autolisp-reference-value*) *autolisp-reference-entry*))

(setq *autolisp-reference-value* "(prin1 [expr [file-desc]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Display Control"))

(setq *autolisp-reference-entry* (cons (cons 'feature-groups *autolisp-reference-value*) *autolisp-reference-entry*))

(setq *autolisp-reference-value* "P")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Prints an expression to the command line or writes an expression to an open file")

(setq *autolisp-reference-entry* (cons (cons 'summary *autolisp-reference-value*) *autolisp-reference-entry*))

(setq *autolisp-reference-value* "prin1 (AutoLISP)")

(setq *autolisp-reference-entry* (cons (cons 'title *autolisp-reference-value*) *autolisp-reference-entry*))

(setq *autolisp-reference-value* "prin1")

(setq *autolisp-reference-entry* (cons (cons 'name *autolisp-reference-value*) *autolisp-reference-entry*))

(setq *autolisp-reference-parts* (cons (list (cons "prin1" *autolisp-reference-entry*)) *autolisp-reference-parts*))

(setq *autolisp-reference-parts*
  (cons
    '(("princ" .
          ((name . "princ")
           (title . "princ (AutoLISP)")
           (summary . "Prints an expression to the command line, or writes an expression to an open file")
           (source-kind . "AutoLISP")
           (alphabetic-group . "P")
           (feature-groups . ("Display Control"))
           (supported-platforms . "Windows and Mac OS")
           (signature . "(princ [expr [file-desc]])")
           (arguments . (("expr" . "Type: Integer, Real, String, List, Symbol, File, Subroutine, Ename (entity name), T, or nil\nA string or AutoLISP expression. Only the specified expr is printed; no newline or space is included.")
                           ("file-desc" . "Type: File or nil\nA file descriptor for a file opened for writing.")))
           (return-values . "Type: Integer, Real, String, List, Symbol, File, Ename (entity name), T, or nil\nThe value of the evaluated expr. If called with no arguments, princ returns a null symbol.")
           (release-information . nil)
           (history . nil)
           (examples . "N/A")
           (url . "https://help.autodesk.com/cloudhelp/2023/ENU/AutoCAD-AutoLISP-Reference/files/GUID-7DDA298B-A97C-49C9-94BA-46C77B50AE99.htm")
           (guid . "GUID-7DDA298B-A97C-49C9-94BA-46C77B50AE99"))))
    *autolisp-reference-parts*))

(setq *autolisp-reference-parts*
  (cons
    '(("print" .
          ((name . "print")
           (title . "print (AutoLISP)")
           (summary . "Prints an expression to the command line, or writes an expression to an open file")
           (source-kind . "AutoLISP")
           (alphabetic-group . "P")
           (feature-groups . ("Display Control"))
           (supported-platforms . "Windows and Mac OS")
           (signature . "(print [expr [file-desc]])")
           (arguments . (("expr" . "Type: Integer, Real, String, List, Symbol, File, Subroutine, Ename (entity name), T, or nil\nA string or AutoLISP expression. Only the specified expr is printed; no newline or space is included.")
                           ("file-desc" . "Type: File or nil\nA file descriptor for a file opened for writing.")))
           (return-values . "Type: Integer, Real, String, List, Symbol, File, Ename (entity name), T, or nil\nThe value of the evaluated expr. If called with no arguments, print returns a null symbol.")
           (release-information . nil)
           (history . nil)
           (examples . "N/A")
           (url . "https://help.autodesk.com/cloudhelp/2023/ENU/AutoCAD-AutoLISP-Reference/files/GUID-4EE74BA9-6ED4-4734-9C47-90A81E0B0971.htm")
           (guid . "GUID-4EE74BA9-6ED4-4734-9C47-90A81E0B0971"))))
    *autolisp-reference-parts*))

(setq *autolisp-reference-parts*
  (cons
    '(("progn" .
          ((name . "progn")
           (title . "progn (AutoLISP)")
           (summary . "Evaluates each expression sequentially and returns the value of the last expression")
           (source-kind . "AutoLISP")
           (alphabetic-group . "P")
           (feature-groups . ("Function-Handling"))
           (supported-platforms . "Windows and Mac OS")
           (signature . "(progn [expr ...])")
           (arguments . (("expr" . "Type: Integer, Real, String, List, Symbol, File, Ename (entity name), T, or nil\nOne or more AutoLISP expressions.")))
           (return-values . "Type: Integer, Real, String, List, Symbol, File, Ename (entity name), T, or nil\nThe result of the last evaluated expression.")
           (release-information . nil)
           (history . nil)
           (examples . "The if function normally evaluates one then expression if the test expression evaluates to anything but nil. The following example uses progn to evaluate two expressions following if:\n\n(if (= a b)\n  (progn\n    (princ \"\\nA = B \")\n    (setq a (+ a 10) b (- b 10))\n  )\n)")
           (url . "https://help.autodesk.com/cloudhelp/2023/ENU/AutoCAD-AutoLISP-Reference/files/GUID-6B2DD269-858D-4C01-ABDB-765DD08284FE.htm")
           (guid . "GUID-6B2DD269-858D-4C01-ABDB-765DD08284FE"))))
    *autolisp-reference-parts*))

(setq *autolisp-reference-parts*
  (cons
    '(("prompt" .
          ((name . "prompt")
           (title . "prompt (AutoLISP)")
           (summary . "Displays a string on your screen's prompt area")
           (source-kind . "AutoLISP")
           (alphabetic-group . "P")
           (feature-groups . ("Display Control"))
           (supported-platforms . "Windows and Mac OS")
           (signature . "(prompt msg)")
           (arguments . (("msg" . "Type: String\nMessage to be displayed to the user.")))
           (return-values . "Type: nil\nAlways returns nil.")
           (release-information . nil)
           (history . nil)
           (examples . "(prompt \"New value: \")\nNew value: nil")
           (url . "https://help.autodesk.com/cloudhelp/2023/ENU/AutoCAD-AutoLISP-Reference/files/GUID-2F702ECF-FEC7-4DEE-8575-88CDEE05F55D.htm")
           (guid . "GUID-2F702ECF-FEC7-4DEE-8575-88CDEE05F55D"))))
    *autolisp-reference-parts*))

(setq *autolisp-reference-parts*
  (cons
    '(("quit" .
          ((name . "quit")
           (title . "quit (AutoLISP)")
           (summary . "Forces the current application to quit")
           (source-kind . "AutoLISP")
           (alphabetic-group . "Q")
           (feature-groups . ("Error-Handling"))
           (supported-platforms . "Windows and Mac OS")
           (signature . "(quit)")
           (arguments . nil)
           (return-values . "Type: nil\nIf quit is called, it returns the error message quit/exit abort and returns to the AutoCAD Command prompt.")
           (release-information . nil)
           (history . nil)
           (examples . "N/A")
           (url . "https://help.autodesk.com/cloudhelp/2023/ENU/AutoCAD-AutoLISP-Reference/files/GUID-E15E32AE-D1FB-41EC-B2C7-AFFD4095842C.htm")
           (guid . "GUID-E15E32AE-D1FB-41EC-B2C7-AFFD4095842C"))))
    *autolisp-reference-parts*))

(setq *autolisp-reference-parts*
  (cons
    '(("quote" .
          ((name . "quote")
           (title . "quote (AutoLISP)")
           (summary . "Returns an expression without evaluating it")
           (source-kind . "AutoLISP")
           (alphabetic-group . "Q")
           (feature-groups . ("Symbol-Handling"))
           (supported-platforms . "Windows and Mac OS")
           (signature . "(quote expr)")
           (arguments . (("expr" . "Type: Integer, Real, String, List, Symbol, File, Subroutine, Ename (entity name), T, or nil\nAn AutoLISP expression.")))
           (return-values . "Type: Integer, Real, String, List, Symbol, File, Subroutine, Ename (entity name), T, or nil\nThe expr argument.")
           (release-information . nil)
           (history . nil)
           (examples . "(quote a)\nA\n\nThe previous expression can also be written as 'a. For example:\n\n!'a\nA\n\n(quote (a b))\n(A B)")
           (url . "https://help.autodesk.com/cloudhelp/2023/ENU/AutoCAD-AutoLISP-Reference/files/GUID-18F7E287-CB2F-4150-9A07-CE23C3F9E604.htm")
           (guid . "GUID-18F7E287-CB2F-4150-9A07-CE23C3F9E604"))))
    *autolisp-reference-parts*))

(setq *autolisp-reference-parts*
  (cons
    '(("read" .
          ((name . "read")
           (title . "read (AutoLISP)")
           (summary . "Returns the first list or atom obtained from a string")
           (source-kind . "AutoLISP")
           (alphabetic-group . "R")
           (feature-groups . ("String-Handling"))
           (supported-platforms . "Windows and Mac OS")
           (signature . "(read [string])")
           (arguments . (("string" . "Type: String\nA text value. The string argument should not contain blanks, except within a list or string.")))
           (return-values . "Type: Integer, Real, List, Symbol, File, T, or nil\nA list or atom. The read function returns its argument converted into the corresponding data type. If no argument is specified, read returns nil.\nIf the string contains multiple AutoLISP expressions separated by AutoLISP symbol delimiters such as blanks, newline, tabs, or parentheses, only the first expression is returned.")
           (release-information . nil)
           (history . nil)
           (examples . "(read \"hello\")\nHELLO\n\n(read \"hello there\")\nHELLO\n\n(read \"\\\"Hi Y'all\\\"\")\n\"Hi Y'all\"\n\n(read \"(a b c)\")\n(A B C)\n\n(read \"(a b c) (d)\")\n(A B C)\n\n(read \"1.2300\")\n1.23\n\n(read \"87\")\n87\n\n(read \"87 3.2\")\n87")
           (url . "https://help.autodesk.com/cloudhelp/2023/ENU/AutoCAD-AutoLISP-Reference/files/GUID-5B50BB3E-C244-46E8-85D8-6A2D48B1FE51.htm")
           (guid . "GUID-5B50BB3E-C244-46E8-85D8-6A2D48B1FE51"))))
    *autolisp-reference-parts*))

(setq *autolisp-reference-entry* nil)

(setq *autolisp-reference-value* "GUID-7E94BD14-F018-47D0-88DA-2B08DE32DB2C")

(setq *autolisp-reference-entry* (cons (cons 'guid *autolisp-reference-value*) *autolisp-reference-entry*))

(setq *autolisp-reference-value* "https://help.autodesk.com/cloudhelp/2023/ENU/AutoCAD-AutoLISP-Reference/files/GUID-7E94BD14-F018-47D0-88DA-2B08DE32DB2C.htm")

(setq *autolisp-reference-entry* (cons (cons 'url *autolisp-reference-value*) *autolisp-reference-entry*))

(setq *autolisp-reference-value* "The following example omits file-desc, so read-char looks for data in the keyboard buffer:\n\n(read-char)\n\nThe keyboard buffer is empty, so read-char waits for user input:\n\nABC\n65\n\nThe user entered ABC; read-char returned the code representing the first character entered (A). The next three calls to read-char return the data remaining in the keyboard input buffer. This data translates to 66 (the code for the letter B), 67 (C), and 10 (newline), respectively:\n\n(read-char)\n66\n\n(read-char)\n67\n\n(read-char)\n10\n\nWith the keyboard input buffer now empty, read-char waits for user input the next time it is called:\n\n(read-char)")

(setq *autolisp-reference-entry* (cons (cons 'examples *autolisp-reference-value*) *autolisp-reference-entry*))

(setq *autolisp-reference-value* "AutoCAD 2021\n- Return value was modified to support Unicode characters and might be different than earlier releases. For example, suppose the \"€\" character was in a file named\n- test.txt\n- . Previously, the value of this character would be returned as ASCII code 128, but with Unicode support the value of this character would be returned as Unicode code 8364.\n- (setq fp (open \"E:\\\\test.txt\" \"r\" \"utf8\"))\n- (read-char fp)\n- 8364\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: Integer\nCharacter code in the range of 1-65536.\nThe read-char function returns a single newline character (code 10) whenever it detects an end-of-line character or character sequence.")

(setq *autolisp-reference-entry* (cons (cons 'return-values *autolisp-reference-value*) *autolisp-reference-entry*))

(setq *autolisp-reference-value* nil)

(setq *autolisp-reference-string* "Type: File\nA file descriptor (obtained from open) referring to an open file. If no file-desc is specified, read-char obtains input from the keyboard input buffer.")

(setq *autolisp-reference-value* (cons (cons "file-desc" *autolisp-reference-string*) *autolisp-reference-value*))

(setq *autolisp-reference-entry* (cons (cons 'arguments *autolisp-reference-value*) *autolisp-reference-entry*))

(setq *autolisp-reference-value* "(read-char [file-desc])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "R")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns the integer representing the character read from the keyboard input buffer or from an open file")

(setq *autolisp-reference-entry* (cons (cons 'summary *autolisp-reference-value*) *autolisp-reference-entry*))

(setq *autolisp-reference-value* "read-char (AutoLISP)")

(setq *autolisp-reference-entry* (cons (cons 'title *autolisp-reference-value*) *autolisp-reference-entry*))

(setq *autolisp-reference-value* "read-char")

(setq *autolisp-reference-entry* (cons (cons 'name *autolisp-reference-value*) *autolisp-reference-entry*))

(setq *autolisp-reference-parts* (cons (list (cons "read-char" *autolisp-reference-entry*)) *autolisp-reference-parts*))

(setq *autolisp-reference-entry* nil)

(setq *autolisp-reference-value* "GUID-AC74D827-0969-4888-91C0-C3149DEC3659")

(setq *autolisp-reference-entry* (cons (cons 'guid *autolisp-reference-value*) *autolisp-reference-entry*))

(setq *autolisp-reference-value* "https://help.autodesk.com/cloudhelp/2023/ENU/AutoCAD-AutoLISP-Reference/files/GUID-AC74D827-0969-4888-91C0-C3149DEC3659.htm")

(setq *autolisp-reference-entry* (cons (cons 'url *autolisp-reference-value*) *autolisp-reference-entry*))

(setq *autolisp-reference-value* "Windows\n\nOpen a file for reading:\n(setq f (open \"c:\\\\my documents\\\\new.tst\" \"r\"))\n#<file \"c:\\\\my documents\\\\new.tst\">\nUse read-line to read a line from the file:\n(read-line f)\n\"To boldly go where nomad has gone before.\"\nObtain a line of input from the user:\n(read-line)\nTo boldly go\n\"To boldly go\"\n\nMac OS\n\nOpen a file for reading:\n(setq f (open \"/my documents/new.tst\" \"r\"))\n#<file \"/my documents/new.tst\">\nCommand:\nUse read-line to read a line from the file:\n(read-line f)\n\"To boldly go where nomad has gone before.\"\nObtain a line of input from the user:\n(read-line)\nTo boldly go\n\"To boldly go\"")

(setq *autolisp-reference-entry* (cons (cons 'examples *autolisp-reference-value*) *autolisp-reference-entry*))

(setq *autolisp-reference-value* "AutoCAD 2021\n- Return value was modified to support Unicode characters and might be different than earlier releases.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: String\nThe text read by read-line, without the end-of-line marker. If read-line encounters the end of the file, it returns nil.")

(setq *autolisp-reference-entry* (cons (cons 'return-values *autolisp-reference-value*) *autolisp-reference-entry*))

(setq *autolisp-reference-value* nil)

(setq *autolisp-reference-string* "Type: File\nA file descriptor (obtained from open) referring to an open file. If no file-desc is specified, read-line obtains input from the keyboard input buffer.")

(setq *autolisp-reference-value* (cons (cons "file-desc" *autolisp-reference-string*) *autolisp-reference-value*))

(setq *autolisp-reference-entry* (cons (cons 'arguments *autolisp-reference-value*) *autolisp-reference-entry*))

(setq *autolisp-reference-value* "(read-line [file-desc])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "R")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Reads a string from the keyboard or from an open file, until an end-of-line marker is encountered")

(setq *autolisp-reference-entry* (cons (cons 'summary *autolisp-reference-value*) *autolisp-reference-entry*))

(setq *autolisp-reference-value* "read-line (AutoLISP)")

(setq *autolisp-reference-entry* (cons (cons 'title *autolisp-reference-value*) *autolisp-reference-entry*))

(setq *autolisp-reference-value* "read-line")

(setq *autolisp-reference-entry* (cons (cons 'name *autolisp-reference-value*) *autolisp-reference-entry*))

(setq *autolisp-reference-parts* (cons (list (cons "read-line" *autolisp-reference-entry*)) *autolisp-reference-parts*))

(setq *autolisp-reference-parts*
  (cons
    '(("redraw" .
          ((name . "redraw")
           (title . "redraw (AutoLISP)")
           (summary . "Redraws the current viewport or a specified object (entity) in the current viewport")
           (source-kind . "AutoLISP")
           (alphabetic-group . "R")
           (feature-groups . ("Display Control"))
           (supported-platforms . "Windows and Mac OS")
           (signature . "(redraw [ename [mode]])")
           (arguments . (("ename" . "Type: ads_name\nThe name of the entity name to be redrawn.")
                           ("mode" . "Type: Integer\nValue that controls the visibility and highlighting of the entity. The mode can be one of the following values:\n1 -- Show entity\n2 -- Hide entity (blank it out)\n3 -- Highlight entity\n4 -- Unhighlight entity\nThe use of entity highlighting (mode 3) must be balanced with entity unhighlighting (mode 4).")))
           (return-values . "Type: nil\nAlways returns nil.")
           (release-information . nil)
           (history . nil)
           (examples . "None")
           (url . "https://help.autodesk.com/cloudhelp/2023/ENU/AutoCAD-AutoLISP-Reference/files/GUID-4A4DCECD-E85A-4860-A58F-56B48227857F.htm")
           (guid . "GUID-4A4DCECD-E85A-4860-A58F-56B48227857F"))))
    *autolisp-reference-parts*))

(setq *autolisp-reference-parts*
  (cons
    '(("regapp" .
          ((name . "regapp")
           (title . "regapp (AutoLISP)")
           (summary . "Registers an application name with the current AutoCAD drawing in preparation for using extended object data")
           (source-kind . "AutoLISP")
           (alphabetic-group . "R")
           (feature-groups . ("Extended Data-Handling"))
           (supported-platforms . "Windows and Mac OS")
           (signature . "(regapp application)")
           (arguments . (("application" . "Type: String\nApplication name. The name must be a valid symbol table name.")))
           (return-values . "Type: String\nIf an application of the same name has already been registered, this function returns nil; otherwise it returns the name of the application.\nIf registered successfully, the application name is entered into the APPID symbol table. This table maintains a list of the applications that are using extended data in the drawing.")
           (release-information . nil)
           (history . nil)
           (examples . "(regapp \"ADESK_4153322344\")\n\"ADESK_4153322344\"\n\n(regapp \"DESIGNER-v2.1-124753\")\n\"DESIGNER-v2.1-124753\"")
           (url . "https://help.autodesk.com/cloudhelp/2023/ENU/AutoCAD-AutoLISP-Reference/files/GUID-D331A88A-9B6E-49C9-B745-D0A063F38FD2.htm")
           (guid . "GUID-D331A88A-9B6E-49C9-B745-D0A063F38FD2"))))
    *autolisp-reference-parts*))

(setq *autolisp-reference-parts*
  (cons
    '(("rem" .
          ((name . "rem")
           (title . "rem (AutoLISP)")
           (summary . "Divides the first number by the second, and returns the remainder")
           (source-kind . "AutoLISP")
           (alphabetic-group . "R")
           (feature-groups . ("Arithmetic"))
           (supported-platforms . "Windows and Mac OS")
           (signature . "(rem [number number ...])")
           (arguments . (("number" . "Type: Integer or Real\nAny number.")))
           (return-values . "Type: Integer or Real\nA number. If any number argument is a real, rem returns a real; otherwise, rem returns an integer. If no arguments are supplied, rem returns 0. If a single number argument is supplied, rem returns number.")
           (release-information . nil)
           (history . nil)
           (examples . "(rem 42 12)\n6\n\n(rem 12.0 16)\n12.0\n\n(rem 26 7 2)\n1")
           (url . "https://help.autodesk.com/cloudhelp/2023/ENU/AutoCAD-AutoLISP-Reference/files/GUID-4CC43BEB-3215-41AE-839B-2DCE6354241A.htm")
           (guid . "GUID-4CC43BEB-3215-41AE-839B-2DCE6354241A"))))
    *autolisp-reference-parts*))

(setq *autolisp-reference-parts*
  (cons
    '(("repeat" .
          ((name . "repeat")
           (title . "repeat (AutoLISP)")
           (summary . "Evaluates each expression a specified number of times, and returns the value of the last expression")
           (source-kind . "AutoLISP")
           (alphabetic-group . "R")
           (feature-groups . ("Equality and Conditional"))
           (supported-platforms . "Windows and Mac OS")
           (signature . "(repeat int [expr ...])")
           (arguments . (("int" . "Type: Integer\nA numeric value. Must be a positive number.")
                           ("expr" . "Type: Integer, Real, String, List, Symbol, File, Ename (entity name), T, or nil\nOne or more atoms or expressions.")))
           (return-values . "Type: Integer, Real, String, List, Symbol, File, Ename (entity name), T, or nil\nThe value of the last expression or atom evaluated. If expr is not supplied, repeat returns nil.")
           (release-information . nil)
           (history . nil)
           (examples . "(setq a 10 b 100)\n100\n\n(repeat 4 (setq a (+ a 10)) (setq b (+ b 100)))\n500\n\nAfter evaluation, a is 50, b is 500, and repeat returns 500.\n\nIf strings are supplied as arguments, repeat returns the last string:\n\n(repeat 100 \"Me\" \"You\")\n\"You\"")
           (url . "https://help.autodesk.com/cloudhelp/2023/ENU/AutoCAD-AutoLISP-Reference/files/GUID-413F72B4-BA37-4E5E-9D51-A0091130A317.htm")
           (guid . "GUID-413F72B4-BA37-4E5E-9D51-A0091130A317"))))
    *autolisp-reference-parts*))

(setq *autolisp-reference-parts*
  (cons
    '(("reverse" .
          ((name . "reverse")
           (title . "reverse (AutoLISP)")
           (summary . "Returns a copy of a list with its elements reversed")
           (source-kind . "AutoLISP")
           (alphabetic-group . "R")
           (feature-groups . ("List Manipulation"))
           (supported-platforms . "Windows and Mac OS")
           (signature . "(reverse lst)")
           (arguments . (("lst" . "Type: List\nA list of the items to reverse.")))
           (return-values . "Type: List\nValues of the lst argument reversed.")
           (release-information . nil)
           (history . nil)
           (examples . "(reverse '((a) b c))\n(C B (A))")
           (url . "https://help.autodesk.com/cloudhelp/2023/ENU/AutoCAD-AutoLISP-Reference/files/GUID-7669E8F1-2A4F-42C7-AAA8-74D1300F9744.htm")
           (guid . "GUID-7669E8F1-2A4F-42C7-AAA8-74D1300F9744"))))
    *autolisp-reference-parts*))

(setq *autolisp-reference-entry* nil)

(setq *autolisp-reference-value* "GUID-D03ABBC2-939A-44DB-8C93-FC63B64DE4A2")

(setq *autolisp-reference-entry* (cons (cons 'guid *autolisp-reference-value*) *autolisp-reference-entry*))

(setq *autolisp-reference-value* "https://help.autodesk.com/cloudhelp/2023/ENU/AutoCAD-AutoLISP-Reference/files/GUID-D03ABBC2-939A-44DB-8C93-FC63B64DE4A2.htm")

(setq *autolisp-reference-entry* (cons (cons 'url *autolisp-reference-value*) *autolisp-reference-entry*))

(setq *autolisp-reference-value* "Set variable x:\n\n(setq x 17.5)\n17.5\n\nConvert the value of x to a string in scientific format, with a precision of 4:\n\n(setq fmtval (rtos x 1 4))\n\"1.7500E+01\"\n\nConvert the value of x to a string in decimal format, with 2 decimal places:\n\n(setq fmtval (rtos x 2 2))\n\"17.50\"\n\nConvert the value of x to a string in engineering format, with a precision of 2:\n\n(setq fmtval (rtos x 3 2))\n\"1'-5.50\\\"\"\n\nConvert the value of x to a string in architectural format:\n\n(setq fmtval (rtos x 4 2))\n\"1'-5 1/2\\\"\"\n\nConvert the value of x to a string in fractional format:\n\n(setq fmtval (rtos x 5 2))\n\"17 1/2\"\n\nSetting AutoCAD UNITMODE system variable to 1 causes units to be displayed as entered. This affects the values returned by rtos for engineering, architectural, and fractional formats, as shown in the following examples:\n\n(setvar \"unitmode\" 1)\n1\n\n(setq fmtva")

(setq *autolisp-reference-value* (strcat *autolisp-reference-value* "l (rtos x 3 2))\n\"1'5.50\\\"\"\n\n(setq fmtval (rtos x 4 2))\n\"1'5-1/2\\\"\"\n\n(setq fmtval (rtos x 5 2))\n\"17-1/2\""))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String\nFormatted numeric value.\nThe AutoCAD UNITMODE system variable affects the returned string when engineering, architectural, or fractional units are selected (mode values 3, 4, or 5).")

(setq *autolisp-reference-entry* (cons (cons 'return-values *autolisp-reference-value*) *autolisp-reference-entry*))

(setq *autolisp-reference-value* nil)

(setq *autolisp-reference-string* "Type: Integer\nPrecision used to format the returned value.")

(setq *autolisp-reference-value* (cons (cons "precision" *autolisp-reference-string*) *autolisp-reference-value*))

(setq *autolisp-reference-string* "Type: Integer\nLinear units mode. The mode corresponds to the values allowed for the AutoCAD LUNITS system variable.\nThe mode can be one of the following numbers:\n1 -- Scientific\n2 -- Decimal\n3 -- Engineering (feet and decimal inches)\n4 -- Architectural (feet and fractional inches)\n5 -- Fractional")

(setq *autolisp-reference-value* (cons (cons "mode" *autolisp-reference-string*) *autolisp-reference-value*))

(setq *autolisp-reference-string* "Type: Integer or Real\nA numeric value.")

(setq *autolisp-reference-value* (cons (cons "number" *autolisp-reference-string*) *autolisp-reference-value*))

(setq *autolisp-reference-entry* (cons (cons 'arguments *autolisp-reference-value*) *autolisp-reference-entry*))

(setq *autolisp-reference-value* "(rtos number [mode [precision]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Conversion"))

(setq *autolisp-reference-entry* (cons (cons 'feature-groups *autolisp-reference-value*) *autolisp-reference-entry*))

(setq *autolisp-reference-value* "R")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Converts a number into a string")

(setq *autolisp-reference-entry* (cons (cons 'summary *autolisp-reference-value*) *autolisp-reference-entry*))

(setq *autolisp-reference-value* "rtos (AutoLISP)")

(setq *autolisp-reference-entry* (cons (cons 'title *autolisp-reference-value*) *autolisp-reference-entry*))

(setq *autolisp-reference-value* "rtos")

(setq *autolisp-reference-entry* (cons (cons 'name *autolisp-reference-value*) *autolisp-reference-entry*))

(setq *autolisp-reference-parts* (cons (list (cons "rtos" *autolisp-reference-entry*)) *autolisp-reference-parts*))

(setq *autolisp-reference-parts*
  (cons
    '(("set" .
          ((name . "set")
           (title . "set (AutoLISP)")
           (summary . "Sets the value of a quoted symbol name to an expression")
           (source-kind . "AutoLISP")
           (alphabetic-group . "S")
           (feature-groups . ("Symbol-Handling"))
           (supported-platforms . "Windows and Mac OS")
           (signature . "(set sym expr)")
           (arguments . (("sym" . "Type: Symbol\nThe user-defined variable to assign expr to.")
                           ("expr" . "Type: Integer, Real, String, List, Symbol, File, Ename (entity name), T, or nil\nAn AutoLISP expression.")))
           (return-values . "Type: Integer, Real, String, List, Symbol, File, Ename (entity name), T, or nil\nThe value of the expression.")
           (release-information . nil)
           (history . nil)
           (examples . "Each of the following commands sets symbol a to 5.0:\n\n(set 'a 5.0)\n5.0\n\n(set (read \"a\") 5.0)\n5.0\n\n(setq a 5.0)\n5.0\n\nBoth set and setq expect a symbol as their first argument, but set accepts an expression that returns a symbol, whereas setq does not, as the following shows:\n\n(set (read \"a\") 5.0)\n5.0\n\n(setq (read \"a\") 5.0)\n; *** ERROR: syntax error")
           (url . "https://help.autodesk.com/cloudhelp/2023/ENU/AutoCAD-AutoLISP-Reference/files/GUID-041BE20B-CFA6-465B-A98B-1BCBDC810881.htm")
           (guid . "GUID-041BE20B-CFA6-465B-A98B-1BCBDC810881"))))
    *autolisp-reference-parts*))

(setq *autolisp-reference-parts*
  (cons
    '(("set_tile" .
          ((name . "set_tile")
           (title . "set_tile (AutoLISP/DCL)")
           (summary . "Sets the value of a dialog box tile")
           (source-kind . "AutoLISP/DCL")
           (alphabetic-group . "S")
           (feature-groups . ("Tile- and Attribute-Handling Functions Reference (AutoLISP/DCL)"))
           (supported-platforms . "Windows and Mac OS")
           (signature . "(set_tile key value)")
           (arguments . (("key" . "Type: String\nValue that specifies a tile. This argument is case-sensitive.")
                           ("value" . "Type: String\nNew value to assign (initially set by the value attribute).")))
           (return-values . "Type: String\nThe value the tile was set to.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-E250DFD4-FA02-47B9-A0BA-C65316E99C17.htm")
           (guid . "GUID-E250DFD4-FA02-47B9-A0BA-C65316E99C17"))))
    *autolisp-reference-parts*))

(setq *autolisp-reference-parts*
  (cons
    '(("setcfg" .
          ((name . "setcfg")
           (title . "setcfg (AutoLISP)")
           (summary . "Obsolete. Writes application data to the AppData section of the acad20xx.cfg file")
           (source-kind . "AutoLISP")
           (alphabetic-group . "S")
           (feature-groups . ("Query and Command"))
           (supported-platforms . "Windows and Mac OS")
           (signature . "(setcfg cfgname cfgval)")
           (arguments . (("cfgname" . "Type: String\nSection and parameter to set with the value of cfgval. The cfgname argument must be a string of the following form:\nAppData/application_name/section_name/.../param_name\nThe string can be up to 496 characters long.")
                           ("cfgval" . "Type: String\nApplication data. The string can be up to 512 characters in length. Larger strings are accepted by setcfg, but cannot be returned by getcfg.")))
           (return-values . "If successful, setcfg returns cfgval. If cfgname is not valid, setcfg returns nil.")
           (release-information . nil)
           (history . nil)
           (examples . "The following code sets the WallThk parameter in the AppData/ArchStuff section to 8, and returns the string “8”:\n\n(setcfg \"AppData/ArchStuff/WallThk\" \"8\")\n\"8\"")
           (url . "https://help.autodesk.com/cloudhelp/2023/ENU/AutoCAD-AutoLISP-Reference/files/GUID-8BABF3B0-C8E1-49C9-A367-9823211C1F6B.htm")
           (guid . "GUID-8BABF3B0-C8E1-49C9-A367-9823211C1F6B"))))
    *autolisp-reference-parts*))

(setq *autolisp-reference-parts*
  (cons
    '(("setenv" .
          ((name . "setenv")
           (title . "setenv (AutoLISP)")
           (summary . "Sets a system environment variable to a specified value")
           (source-kind . "AutoLISP")
           (alphabetic-group . "S")
           (feature-groups . ("Query and Command"))
           (supported-platforms . "Windows and Mac OS")
           (signature . "(setenv varname value)")
           (arguments . (("varname" . "Type: String\nName of the environment variable to be set. Environment variable names must be spelled and cased exactly as they are stored in the system registry.")
                           ("value" . "Type: String\nValue to set varname to.")))
           (return-values . "Type: String\nValue provided with the value argument.")
           (release-information . nil)
           (history . nil)
           (examples . "The following command sets the value of the MaxArray environment variable to 10000:\n\n(setenv \"MaxArray\" \"10000\")\n\"10000\"\n\nNote that changes to settings might not take effect until the next time AutoCAD is started.")
           (url . "https://help.autodesk.com/cloudhelp/2023/ENU/AutoCAD-AutoLISP-Reference/files/GUID-0C2E8222-62A8-4529-8A8A-58AAB2A5F23B.htm")
           (guid . "GUID-0C2E8222-62A8-4529-8A8A-58AAB2A5F23B"))))
    *autolisp-reference-parts*))

(setq *autolisp-reference-entry* nil)

(setq *autolisp-reference-value* "GUID-61B2326A-8DE4-46C4-B9F9-22B8D163A761")

(setq *autolisp-reference-entry* (cons (cons 'guid *autolisp-reference-value*) *autolisp-reference-entry*))

(setq *autolisp-reference-value* "https://help.autodesk.com/cloudhelp/2023/ENU/AutoCAD-AutoLISP-Reference/files/GUID-61B2326A-8DE4-46C4-B9F9-22B8D163A761.htm")

(setq *autolisp-reference-entry* (cons (cons 'url *autolisp-reference-value*) *autolisp-reference-entry*))

(setq *autolisp-reference-value* "The following example illustrates the use of setfunhelp by defining a simple function and issuing setfunhelp to associate the function with the Entget topic in the AutoCAD Help file (acad.chm):\n\n(defun c:foo ()\n  (getstring \"Press F1 for help on the foo command:\")\n)\n(setfunhelp \"c:test\" \"acad.chm\" \"entget\")\n\nAfter this code is loaded, issuing the foo command and then pressing F1 displays the circle topic.\n\nThis example works, but serves no real purpose. In the real world, you would create your own Help file and associate that Help file and topic with your function.\n\nDefine a function named test:\n\n(defun c:test()(getstring \"\\nTEST: \" )(princ))\nC:TEST\n\nAssociate the function with a call to Help with the string “line”:\n\n(setfunhelp \"c:test\" \"acad_acr.chm\" \"line\")\n\"c:test\"\n\nRun the test command and at the prompt, press F1; you should see the Help topic")

(setq *autolisp-reference-value* (strcat *autolisp-reference-value* " for the AutoCAD LINE command."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String or nil\nc:fname, if successful; otherwise, nil.\nThis function verifies only that the c:fname argument has the c: prefix. It does not verify that the c:fname function exists, nor does it verify the correctness of the other arguments supplied.")

(setq *autolisp-reference-entry* (cons (cons 'return-values *autolisp-reference-value*) *autolisp-reference-entry*))

(setq *autolisp-reference-value* nil)

(setq *autolisp-reference-string* "Type: String\nInitial state of the Help window. The command argument is a string used by the uCommand (in HTML Help) or the fuCommand (in WinHelp) argument of the HtmlHelp() and WinHelp() functions as defined in the Microsoft Windows SDK.\nFor HTML Help files, the command parameter can be HH_ALINK_LOOKUP or HH_DISPLAY_TOPIC. For Windows Help files, the command parameter can be HELP_CONTENTS, HELP_HELPONHELP, or HELP_PARTIALKEY.")

(setq *autolisp-reference-value* (cons (cons "command" *autolisp-reference-string*) *autolisp-reference-value*))

(setq *autolisp-reference-string* "Type: String\nHelp topic ID. If you are calling a topic within a CHM file, provide the file name without the extension; AutoCAD adds an .htm extension.")

(setq *autolisp-reference-value* (cons (cons "topic" *autolisp-reference-string*) *autolisp-reference-value*))

(setq *autolisp-reference-string* "Type: String\nHelp file name. The file extension is not required with the helpfile argument. If a file extension is provided, AutoCAD looks only for a file with the exact name specified.\nIf no file extension is provided, AutoCAD looks for helpfile with an extension of .chm. If no file of that name is found, AutoCAD looks for a file with an extension of .hlp.")

(setq *autolisp-reference-value* (cons (cons "helpfile" *autolisp-reference-string*) *autolisp-reference-value*))

(setq *autolisp-reference-string* "Type: String\nUser-defined command (the C:XXXfunction). You must include the c: prefix.")

(setq *autolisp-reference-value* (cons (cons "c:fname" *autolisp-reference-string*) *autolisp-reference-value*))

(setq *autolisp-reference-entry* (cons (cons 'arguments *autolisp-reference-value*) *autolisp-reference-entry*))

(setq *autolisp-reference-value* "(setfunhelp c:fname [helpfile [topic [command]]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Query and Command"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Registers a user-defined command with the Help facility so the appropriate Help file and topic are called when the user requests help on that command")

(setq *autolisp-reference-entry* (cons (cons 'summary *autolisp-reference-value*) *autolisp-reference-entry*))

(setq *autolisp-reference-value* "setfunhelp (AutoLISP)")

(setq *autolisp-reference-entry* (cons (cons 'title *autolisp-reference-value*) *autolisp-reference-entry*))

(setq *autolisp-reference-value* "setfunhelp")

(setq *autolisp-reference-entry* (cons (cons 'name *autolisp-reference-value*) *autolisp-reference-entry*))

(setq *autolisp-reference-parts* (cons (list (cons "setfunhelp" *autolisp-reference-entry*)) *autolisp-reference-parts*))

(setq *autolisp-reference-entry* nil)

(setq *autolisp-reference-value* "GUID-8F32FD8C-D81A-4DCA-B455-9D560CF17246")

(setq *autolisp-reference-entry* (cons (cons 'guid *autolisp-reference-value*) *autolisp-reference-entry*))

(setq *autolisp-reference-value* "https://help.autodesk.com/cloudhelp/2023/ENU/AutoCAD-AutoLISP-Reference/files/GUID-8F32FD8C-D81A-4DCA-B455-9D560CF17246.htm")

(setq *autolisp-reference-entry* (cons (cons 'url *autolisp-reference-value*) *autolisp-reference-entry*))

(setq *autolisp-reference-value* "The following example demonstrates how to change the radius of a circle.\n\n(command \"._circle\" \"2,2\" 2)\nnil\n\n(setpropertyvalue (entlast) \"radius\" 3)\nnil\n\nThe following example demonstrates how to apply overrides to a linear dimension.\n\n(command \"._dimlinear\" \"2,2\" \"5,4\" \"3,3\")\nnil\n\n(setq e2 (entlast))\n<Entity name: 10e2e4bd0>\n\n(setpropertyvalue e2 \"Dimtfill\" 2)\nnil\n\n(setpropertyvalue e2 \"Dimtfillclr\" \"2\")\nnil\n\n(setpropertyvalue e2 \"Dimclrt\" \"255,0,0\")\nnil\n\nThe following example demonstrates how to change the first vertex of the Vertices collection.\n\n(command \"._pline\" \"0,0\" \"3,3\" \"5,2\" \"\")\nnil\n\n(setq e3 (entlast))\n<Entity name: 10e2e4da0>\n\n(setpropertyvalue e3 \"Vertices\" 0 \"EndWidth\" 1.0)\nnil")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: nil\nnil is returned unless an error occurs when the property value is being updated.")

(setq *autolisp-reference-entry* (cons (cons 'return-values *autolisp-reference-value*) *autolisp-reference-entry*))

(setq *autolisp-reference-value* nil)

(setq *autolisp-reference-string* "Type: Integer, Real, String, List, T, or nil\nValue to set the property to.")

(setq *autolisp-reference-value* (cons (cons "val" *autolisp-reference-string*) *autolisp-reference-value*))

(setq *autolisp-reference-string* "Type: String\nName of the property in the collection to be modified.")

(setq *autolisp-reference-value* (cons (cons "name" *autolisp-reference-string*) *autolisp-reference-value*))

(setq *autolisp-reference-string* "Type: Integer\nThe collection index to be modified.")

(setq *autolisp-reference-value* (cons (cons "index" *autolisp-reference-string*) *autolisp-reference-value*))

(setq *autolisp-reference-string* "Type: String\nIf the object is a collection object, the Collection name is passed here.")

(setq *autolisp-reference-value* (cons (cons "collectionName" *autolisp-reference-string*) *autolisp-reference-value*))

(setq *autolisp-reference-string* "Type: Integer, Real, String, List, T, or nil\nValue to set the property to when the object is not a collection.")

(setq *autolisp-reference-value* (cons (cons "value" *autolisp-reference-string*) *autolisp-reference-value*))

(setq *autolisp-reference-string* "Type: String\nName of the property to be modified. For a list of all the valid property names of a given object, use dumpallproperties.")

(setq *autolisp-reference-value* (cons (cons "propertyname" *autolisp-reference-string*) *autolisp-reference-value*))

(setq *autolisp-reference-string* "Type: Ename (entity name)\nName of the entity being modified. The ename can refer to either a graphical or a non-graphical entity.")

(setq *autolisp-reference-value* (cons (cons "ename" *autolisp-reference-string*) *autolisp-reference-value*))

(setq *autolisp-reference-entry* (cons (cons 'arguments *autolisp-reference-value*) *autolisp-reference-entry*))

(setq *autolisp-reference-value* "(setpropertyvalue ename propertyname value [or collectionName index name val])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Object-Handling"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Sets the property value for an entity")

(setq *autolisp-reference-entry* (cons (cons 'summary *autolisp-reference-value*) *autolisp-reference-entry*))

(setq *autolisp-reference-value* "setpropertyvalue (AutoLISP)")

(setq *autolisp-reference-entry* (cons (cons 'title *autolisp-reference-value*) *autolisp-reference-entry*))

(setq *autolisp-reference-value* "setpropertyvalue")

(setq *autolisp-reference-entry* (cons (cons 'name *autolisp-reference-value*) *autolisp-reference-entry*))

(setq *autolisp-reference-parts* (cons (list (cons "setpropertyvalue" *autolisp-reference-entry*)) *autolisp-reference-parts*))

(setq *autolisp-reference-parts*
  (cons
    '(("setq" .
          ((name . "setq")
           (title . "setq (AutoLISP)")
           (summary . "Sets the value of a symbol or symbols to associated expressions")
           (source-kind . "AutoLISP")
           (alphabetic-group . "S")
           (feature-groups . ("Symbol-Handling"))
           (supported-platforms . "Windows and Mac OS")
           (signature . "(setq sym expr [sym expr] ...)")
           (arguments . (("sym" . "Type: Symbol\nThe user-defined variable to assign expr to. This argument is not evaluated.")
                           ("expr" . "Type: Integer, Real, String, List, File, Ename (entity name), T, or nil\nAn expression.")))
           (return-values . "Type: Integer, Real, String, List, File, Ename (entity name), T, or nil\nThe result of the last expr evaluated.")
           (release-information . nil)
           (history . nil)
           (examples . "The following function call sets variable a to 5.0:\n\n(setq a 5.0)\n5.0\n\nWhenever a is evaluated, it returns the real number 5.0.\n\nThe following command sets two variables, b and c:\n\n(setq b 123 c 4.7)\n4.7\n\nsetq returns the value of the last variable set.\n\nIn the following example, s is set to a string:\n\n(setq s \"it\")\n\"it\"\n\nThe following example assigns a list to x:\n\n(setq x '(a b))\n(A B)")
           (url . "https://help.autodesk.com/cloudhelp/2023/ENU/AutoCAD-AutoLISP-Reference/files/GUID-2F4B7A7B-7B6F-4E1C-B32E-677506094EAA.htm")
           (guid . "GUID-2F4B7A7B-7B6F-4E1C-B32E-677506094EAA"))))
    *autolisp-reference-parts*))

(setq *autolisp-reference-parts*
  (cons
    '(("setvar" .
          ((name . "setvar")
           (title . "setvar (AutoLISP)")
           (summary . "Sets an AutoCAD system variable to a specified value")
           (source-kind . "AutoLISP")
           (alphabetic-group . "S")
           (feature-groups . ("Query and Command"))
           (supported-platforms . "Windows and Mac OS")
           (signature . "(setvar varname value)")
           (arguments . (("varname" . "Type: String\nSystem variable name.\nYou can find a list of the current AutoCAD system variables in the product Help.")
                           ("value" . "Type: Integer, Real, String, List, T, or nil\nAn atom or expression whose evaluated result is to be assigned to varname. For system variables with integer values, the supplied value must be between -32,768 and +32,767.")))
           (return-values . "Type: Integer, Real, String, List, T, or nil\nIf successful, setvar returns value.")
           (release-information . nil)
           (history . nil)
           (examples . "Set the AutoCAD fillet radius to 0.5 units:\n\n(setvar \"FILLETRAD\" 0.50)\n0.5")
           (url . "https://help.autodesk.com/cloudhelp/2023/ENU/AutoCAD-AutoLISP-Reference/files/GUID-B1CE1BFB-2448-47F1-95EC-10E9509F01FA.htm")
           (guid . "GUID-B1CE1BFB-2448-47F1-95EC-10E9509F01FA"))))
    *autolisp-reference-parts*))

(setq *autolisp-reference-parts*
  (cons
    '(("setview" .
          ((name . "setview")
           (title . "setview (AutoLISP)")
           (summary . "Establishes a view for a specified viewport")
           (source-kind . "AutoLISP")
           (alphabetic-group . "S")
           (feature-groups . ("Symbol Table and Dictionary-Handling"))
           (supported-platforms . "Windows and Mac OS")
           (signature . "(setview view_descriptor [vport_id])")
           (arguments . (("view_descriptor" . "Type: Ename (entity name)\nAn entity definition list similar to that returned by tblsearch when applied to the VIEW symbol table.")
                           ("vport_id" . "Type: Integer\nViewport to receive the new view. If vport_id is 0, the current viewport receives the new view.\nYou can obtain the vport_id number from the AutoCAD CVPORT system variable.")))
           (return-values . "Type: Ename (entity name) or nil\nIf successful, the setview function returns the view_descriptor.")
           (release-information . nil)
           (history . nil)
           (examples . "N/A")
           (url . "https://help.autodesk.com/cloudhelp/2023/ENU/AutoCAD-AutoLISP-Reference/files/GUID-EEABEF66-423A-4D2B-BE16-AA6A56B08FBD.htm")
           (guid . "GUID-EEABEF66-423A-4D2B-BE16-AA6A56B08FBD"))))
    *autolisp-reference-parts*))

(setq *autolisp-reference-parts*
  (cons
    '(("showhtmlmodalwindow" .
          ((name . "showhtmlmodalwindow")
           (title . "showhtmlmodalwindow (AutoLISP)")
           (summary . "Displays a modal dialog box with a specified URI (Uniform Resource Identifier)")
           (source-kind . "AutoLISP")
           (alphabetic-group . "S")
           (feature-groups . ("Application-Handling"))
           (supported-platforms . "Windows only")
           (signature . "(showhtmlmodalwindow uri)")
           (arguments . (("uri" . "Type: String\nURI of the page to be loaded into the dialog box.\nThe page that the URI references can utilize the AutoCAD JavaScript API.")))
           (return-values . "Type: nil\nAlways returns nil.")
           (release-information . nil)
           (history . nil)
           (examples . "The following example displays the AutoCAD Developer Center.\n\n(showhtmlmodalwindow \"https://www.autodesk.com/developautocad\")")
           (url . "https://help.autodesk.com/cloudhelp/2023/ENU/AutoCAD-AutoLISP-Reference/files/GUID-1330BB1E-866E-419A-8AE3-22B0C16E1F06.htm")
           (guid . "GUID-1330BB1E-866E-419A-8AE3-22B0C16E1F06"))))
    *autolisp-reference-parts*))

(setq *autolisp-reference-parts*
  (cons
    '(("sin" .
          ((name . "sin")
           (title . "sin (AutoLISP)")
           (summary . "Returns the sine of an angle as a real number expressed in radians")
           (source-kind . "AutoLISP")
           (alphabetic-group . "S")
           (feature-groups . ("Arithmetic"))
           (supported-platforms . "Windows and Mac OS")
           (signature . "(sin ang)")
           (arguments . (("ang" . "Type: Integer or Real\nAn angle, in radians.")))
           (return-values . "Type: Real\nA number representing the sine of ang, in radians.")
           (release-information . nil)
           (history . nil)
           (examples . "(sin 1.0)\n0.841471\n\n(sin 0.0)\n0.0")
           (url . "https://help.autodesk.com/cloudhelp/2023/ENU/AutoCAD-AutoLISP-Reference/files/GUID-83677851-6FA5-496E-A93C-AEA55ABCB527.htm")
           (guid . "GUID-83677851-6FA5-496E-A93C-AEA55ABCB527"))))
    *autolisp-reference-parts*))

(setq *autolisp-reference-entry* nil)

(setq *autolisp-reference-value* "GUID-D5B5A0AF-82BE-4A00-832D-04D496D809D0")

(setq *autolisp-reference-entry* (cons (cons 'guid *autolisp-reference-value*) *autolisp-reference-entry*))

(setq *autolisp-reference-value* "https://help.autodesk.com/cloudhelp/2023/ENU/AutoCAD-AutoLISP-Reference/files/GUID-D5B5A0AF-82BE-4A00-832D-04D496D809D0.htm")

(setq *autolisp-reference-entry* (cons (cons 'url *autolisp-reference-value*) *autolisp-reference-entry*))

(setq *autolisp-reference-value* "(slide_image\n  0\n  0\n  (dimx_tile \"slide_tile\")\n  (dimy_tile \"slide_tile\")\n  \"myslide\"\n)\n(end_image)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* "Releases:\n- AutoCAD R12 and later on Windows")

(setq *autolisp-reference-entry* (cons (cons 'release-information *autolisp-reference-value*) *autolisp-reference-entry*))

(setq *autolisp-reference-value* "Type: String\nA value containing sldname.")

(setq *autolisp-reference-entry* (cons (cons 'return-values *autolisp-reference-value*) *autolisp-reference-entry*))

(setq *autolisp-reference-value* nil)

(setq *autolisp-reference-string* "Type: String\nIdentifies the slide. This argument can be a slide file (.sld) or a slide in a slide library file (.slb). Specify sldname the same way you would specify it for the AutoCAD VSLIDE command or for a customization file. Use one of the following formats for sldname:\nsldname or libname(sldname)")

(setq *autolisp-reference-value* (cons (cons "sldname" *autolisp-reference-string*) *autolisp-reference-value*))

(setq *autolisp-reference-string* "Type: Integer\nHeight of the image, in pixels.")

(setq *autolisp-reference-value* (cons (cons "height" *autolisp-reference-string*) *autolisp-reference-value*))

(setq *autolisp-reference-string* "Type: Integer\nWidth of the image, in pixels.")

(setq *autolisp-reference-value* (cons (cons "width" *autolisp-reference-string*) *autolisp-reference-value*))

(setq *autolisp-reference-string* "Type: Integer\nY-offset from the upper-left corner of the tile, in pixels. Must be a positive value.")

(setq *autolisp-reference-value* (cons (cons "y1" *autolisp-reference-string*) *autolisp-reference-value*))

(setq *autolisp-reference-string* "Type: Integer\nX-offset from the upper-left corner of the tile, in pixels. Must be a positive value.")

(setq *autolisp-reference-value* (cons (cons "x1" *autolisp-reference-string*) *autolisp-reference-value*))

(setq *autolisp-reference-entry* (cons (cons 'arguments *autolisp-reference-value*) *autolisp-reference-entry*))

(setq *autolisp-reference-value* "(slide_image x1 y1 width height sldname)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Image Tile-Handling Functions Reference (AutoLISP/DCL)"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP/DCL")

(setq *autolisp-reference-entry* (cons (cons 'source-kind *autolisp-reference-value*) *autolisp-reference-entry*))

(setq *autolisp-reference-value* "Displays an AutoCAD slide in the currently active dialog box image tile")

(setq *autolisp-reference-entry* (cons (cons 'summary *autolisp-reference-value*) *autolisp-reference-entry*))

(setq *autolisp-reference-value* "slide_image (AutoLISP/DCL)")

(setq *autolisp-reference-entry* (cons (cons 'title *autolisp-reference-value*) *autolisp-reference-entry*))

(setq *autolisp-reference-value* "slide_image")

(setq *autolisp-reference-entry* (cons (cons 'name *autolisp-reference-value*) *autolisp-reference-entry*))

(setq *autolisp-reference-parts* (cons (list (cons "slide_image" *autolisp-reference-entry*)) *autolisp-reference-parts*))

(setq *autolisp-reference-entry* nil)

(setq *autolisp-reference-value* "GUID-2EFBE198-9860-456B-A090-206C743ACB90")

(setq *autolisp-reference-entry* (cons (cons 'guid *autolisp-reference-value*) *autolisp-reference-entry*))

(setq *autolisp-reference-value* "https://help.autodesk.com/cloudhelp/2023/ENU/AutoCAD-AutoLISP-Reference/files/GUID-2EFBE198-9860-456B-A090-206C743ACB90.htm")

(setq *autolisp-reference-entry* (cons (cons 'url *autolisp-reference-value*) *autolisp-reference-entry*))

(setq *autolisp-reference-value* "The following examples assume EXTNAMES is set to 1:\n\n(snvalid \"hocus-pocus\")\nT\n\n(snvalid \"hocus pocus\")\nT\n\n(snvalid \"hocus%pocus\")\nT\n\nThe following examples assume EXTNAMES is set to 0:\n\n(snvalid \"hocus-pocus\")\nT\n\n(snvalid \"hocus pocus\")\nnil\n\n(snvalid \"hocus%pocus\")\nnil\n\nThe following example includes a vertical bar in the symbol table name:\n\n(snvalid \"hocus|pocus\")\nnil\n\nBy default, the vertical bar character is considered invalid in all symbol table names.\n\nIn the following example, the flag argument is set to 1, so snvalid considers the vertical bar character to be valid in sym_name, as long as it is not the first or last character in the name:\n\n(snvalid \"hocus|pocus\" 1)\nT")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nT, if sym_name is a valid symbol table name; otherwise nil.")

(setq *autolisp-reference-entry* (cons (cons 'return-values *autolisp-reference-value*) *autolisp-reference-entry*))

(setq *autolisp-reference-value* nil)

(setq *autolisp-reference-string* "Type: Integer\nSpecifies whether the vertical bar character is allowed within sym_name. The flag argument can be one of the following:\n0 -- Do not allow vertical bar characters anywhere in sym_name. This is the default.\n1 -- Allow vertical bar characters in sym_name, as long as they are not the first or last characters in the name.")

(setq *autolisp-reference-value* (cons (cons "flag" *autolisp-reference-string*) *autolisp-reference-value*))

(setq *autolisp-reference-string* "Type: String\nSymbol table name.")

(setq *autolisp-reference-value* (cons (cons "sym_name" *autolisp-reference-string*) *autolisp-reference-value*))

(setq *autolisp-reference-entry* (cons (cons 'arguments *autolisp-reference-value*) *autolisp-reference-entry*))

(setq *autolisp-reference-value* "(snvalid sym_name [flag])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Symbol Table and Dictionary-Handling"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Checks the symbol table name for valid characters")

(setq *autolisp-reference-entry* (cons (cons 'summary *autolisp-reference-value*) *autolisp-reference-entry*))

(setq *autolisp-reference-value* "snvalid (AutoLISP)")

(setq *autolisp-reference-entry* (cons (cons 'title *autolisp-reference-value*) *autolisp-reference-entry*))

(setq *autolisp-reference-value* "snvalid")

(setq *autolisp-reference-entry* (cons (cons 'name *autolisp-reference-value*) *autolisp-reference-entry*))

(setq *autolisp-reference-parts* (cons (list (cons "snvalid" *autolisp-reference-entry*)) *autolisp-reference-parts*))

(setq *autolisp-reference-parts*
  (cons
    '(("sqrt" .
          ((name . "sqrt")
           (title . "sqrt (AutoLISP)")
           (summary . "Returns the square root of a number as a real number")
           (source-kind . "AutoLISP")
           (alphabetic-group . "S")
           (feature-groups . ("Arithmetic"))
           (supported-platforms . "Windows and Mac OS")
           (signature . "(sqrt num)")
           (arguments . (("num" . "Type: Integer or Real\nA numeric value.")))
           (return-values . "Type: Integer or Real\nA numeric value based on the square root of num.")
           (release-information . nil)
           (history . nil)
           (examples . "(sqrt 4)\n2.0\n\n(sqrt 2.0)\n1.41421")
           (url . "https://help.autodesk.com/cloudhelp/2023/ENU/AutoCAD-AutoLISP-Reference/files/GUID-B8D3BA69-95FE-4036-83BA-6AFEA45BADE5.htm")
           (guid . "GUID-B8D3BA69-95FE-4036-83BA-6AFEA45BADE5"))))
    *autolisp-reference-parts*))

(setq *autolisp-reference-entry* nil)

(setq *autolisp-reference-value* "GUID-22337977-82F2-4394-B209-39DE2B4B9E86")

(setq *autolisp-reference-entry* (cons (cons 'guid *autolisp-reference-value*) *autolisp-reference-entry*))

(setq *autolisp-reference-value* "https://help.autodesk.com/cloudhelp/2023/ENU/AutoCAD-AutoLISP-Reference/files/GUID-22337977-82F2-4394-B209-39DE2B4B9E86.htm")

(setq *autolisp-reference-entry* (cons (cons 'url *autolisp-reference-value*) *autolisp-reference-entry*))

(setq *autolisp-reference-value* "When adding an entity to a set, the new entity is added to the existing set, and the set passed as ss is returned as the result. Thus, if the set is assigned to other variables, they also reflect the addition. If the named entity is already in the set, the ssadd operation is ignored and no error is reported.\n\nSet e1 to the name of the first entity in drawing:\n\n(setq e1 (entnext))\n<Entity name: 1d62d60>\n\nSet ss to a null selection set:\n\n(setq ss (ssadd))\n<Selection set: 2>\n\nThe following command adds the e1 entity to the selection set referenced by ss:\n\n(ssadd e1 ss)\n<Selection set: 2>\n\nGet the entity following e1:\n\n(setq e2 (entnext e1))\n<Entity name: 1d62d68>\n\nAdd e2 to the ss entity:\n\n(ssadd e2 ss)\n<Selection set: 2>")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Pickset (selection set) or nil\nThe modified selection set passed as the second argument, if successful; otherwise nil.")

(setq *autolisp-reference-entry* (cons (cons 'return-values *autolisp-reference-value*) *autolisp-reference-entry*))

(setq *autolisp-reference-value* nil)

(setq *autolisp-reference-string* "Type: Pickset (selection set)\nA selection set.")

(setq *autolisp-reference-value* (cons (cons "ss" *autolisp-reference-string*) *autolisp-reference-value*))

(setq *autolisp-reference-string* "Type: Ename (entity name)\nAn entity name.")

(setq *autolisp-reference-value* (cons (cons "ename" *autolisp-reference-string*) *autolisp-reference-value*))

(setq *autolisp-reference-entry* (cons (cons 'arguments *autolisp-reference-value*) *autolisp-reference-entry*))

(setq *autolisp-reference-value* "(ssadd [ename [ss]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Selection Set Manipulation"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Adds an object (entity) to a selection set, or creates a new selection set")

(setq *autolisp-reference-entry* (cons (cons 'summary *autolisp-reference-value*) *autolisp-reference-entry*))

(setq *autolisp-reference-value* "ssadd (AutoLISP)")

(setq *autolisp-reference-entry* (cons (cons 'title *autolisp-reference-value*) *autolisp-reference-entry*))

(setq *autolisp-reference-value* "ssadd")

(setq *autolisp-reference-entry* (cons (cons 'name *autolisp-reference-value*) *autolisp-reference-entry*))

(setq *autolisp-reference-parts* (cons (list (cons "ssadd" *autolisp-reference-entry*)) *autolisp-reference-parts*))

(setq *autolisp-reference-parts*
  (cons
    '(("ssdel" .
          ((name . "ssdel")
           (title . "ssdel (AutoLISP)")
           (summary . "Deletes an object (entity) from a selection set")
           (source-kind . "AutoLISP")
           (alphabetic-group . "S")
           (feature-groups . ("Selection Set Manipulation"))
           (supported-platforms . "Windows and Mac OS")
           (signature . "(ssdel ename ss)")
           (arguments . (("ename" . "Type: Ename (entity name)\nAn entity name.")
                           ("ss" . "Type: Pickset (selection set)\nA selection set.")))
           (return-values . "Type: Pickset (selection set) or nil\nThe name of the selection set; otherwise nil, if the specified entity is not in the set.\nNote that the entity is actually deleted from the existing selection set, as opposed to a new set being returned with the element deleted.")
           (release-information . nil)
           (history . nil)
           (examples . "In the following examples, entity name e1 is a member of selection set ss, while entity name e3 is not a member of ss:\n\n(ssdel e1 ss)\n<Selection set: 2>\n\nSelection set ss is returned with entity e1 removed.\n\n(ssdel e3 ss)\nnil\n\nThe function returns nil because e3 is not a member of selection set ss.")
           (url . "https://help.autodesk.com/cloudhelp/2023/ENU/AutoCAD-AutoLISP-Reference/files/GUID-F84DB8CE-B535-453D-977D-AE9D7AD2D7AA.htm")
           (guid . "GUID-F84DB8CE-B535-453D-977D-AE9D7AD2D7AA"))))
    *autolisp-reference-parts*))

(setq *autolisp-reference-entry* nil)

(setq *autolisp-reference-value* "GUID-0F37CC5E-1559-4011-B8CF-A3BA0973B2C3")

(setq *autolisp-reference-entry* (cons (cons 'guid *autolisp-reference-value*) *autolisp-reference-entry*))

(setq *autolisp-reference-value* "https://help.autodesk.com/cloudhelp/2023/ENU/AutoCAD-AutoLISP-Reference/files/GUID-0F37CC5E-1559-4011-B8CF-A3BA0973B2C3.htm")

(setq *autolisp-reference-entry* (cons (cons 'url *autolisp-reference-value*) *autolisp-reference-entry*))

(setq *autolisp-reference-value* "Prompt the user to select the objects to be placed in a selection set:\n\n(ssget)\n<Selection set: 2>\n\nCreate a selection set of the object passing through (2,2):\n\n(ssget '(2 2))\nnil\n\nCreate a selection set of the most recently selected objects:\n\n(ssget \"_P\")\n<Selection set: 4>\n\nCreate a selection set of the objects crossing the box from (0,0) to (1,1):\n\n(ssget \"_C\" '(0 0) '(1 1))\n<Selection set: b>\n\nCreate a selection set of the objects inside the window from (0,0):\n\n(ssget \"_W\" '(0 0) '(5 5))\n<Selection set: d>\n\nBy specifying filters, you can obtain a selection set that includes all objects of a given type, on a given layer, or of a given color. The following example returns a selection set that consists only of blue lines that are part of the implied selection set (those objects selected while the AutoCAD PICKFIRST system variable is in effect):\n\n(ssget ")

(setq *autolisp-reference-value* (strcat *autolisp-reference-value* "\"_I\" '((0 . \"LINE\") (62 . 5)))\n<Selection set: 4>\n\nThe following examples of ssget require that a list of points be passed to the function. The pt_list variable cannot contain points that define zero-length segments.\n\nCreate a list of points:\n\n(setq pt_list '((1 1)(3 1)(5 2)(2 4)))\n((1 1) (3 1) (5 2) (2 4))\n\nCreate a selection set of all objects crossing and inside the polygon defined by pt_list:\n\n(ssget \"_CP\" pt_list)\n<Selection set: 13>\n\nCreate a selection set of all blue lines inside the polygon defined by pt_list:\n\n(ssget \"_WP\" pt_list '((0 . \"LINE\") (62 . 5)))\n<Selection set: 8>\n\nThe selected objects are highlighted only when ssget is used with no arguments. Selection sets consume AutoCAD temporary file slots, so AutoLISP is not permitted to have more than 128 open at one time. If this limit is reached, AutoCAD cannot create any more selection sets and "))

(setq *autolisp-reference-value* (strcat *autolisp-reference-value* "returns nil to all ssget calls. To close an unnecessary selection set variable, set it to nil.\n\nA selection set variable can be passed to AutoCAD in response to any Select objects prompt at which selection by Last is valid. AutoCAD then selects all the objects in the selection set variable.\n\nThe current setting of Object Snap mode is ignored by ssget unless you specifically request it while you are in the function."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Pickset (selection set) or nil\nThe name of the created selection set if successful; otherwise nil if no objects were selected.")

(setq *autolisp-reference-entry* (cons (cons 'return-values *autolisp-reference-value*) *autolisp-reference-entry*))

(setq *autolisp-reference-value* nil)

(setq *autolisp-reference-string* "Type: List\nAn association list that specifies object properties. Objects that match the filter-list are added to the selection set.")

(setq *autolisp-reference-value* (cons (cons "filter-list" *autolisp-reference-string*) *autolisp-reference-value*))

(setq *autolisp-reference-string* "Type: List\nA list of points.")

(setq *autolisp-reference-value* (cons (cons "pt-list" *autolisp-reference-string*) *autolisp-reference-value*))

(setq *autolisp-reference-string* "Type: List\nA point relative to the selection.")

(setq *autolisp-reference-value* (cons (cons "pt2" *autolisp-reference-string*) *autolisp-reference-value*))

(setq *autolisp-reference-string* "Type: List\nA point relative to the selection.")

(setq *autolisp-reference-value* (cons (cons "pt1" *autolisp-reference-string*) *autolisp-reference-value*))

(setq *autolisp-reference-string* "Type: String\nObject selection method.\nValid selection methods are")

(setq *autolisp-reference-value* (cons (cons "sel-method" *autolisp-reference-string*) *autolisp-reference-value*))

(setq *autolisp-reference-entry* (cons (cons 'arguments *autolisp-reference-value*) *autolisp-reference-entry*))

(setq *autolisp-reference-value* "(ssget [sel-method] [pt1 [pt2]] [pt-list] [filter-list])\n\n;; Allow for a single selection\n(ssget \"_:S\")\n\nSelect objects: ?\n*Invalid selection*\nExpects a point or Window/Last/Crossing/BOX/ALL/Fence/WPolygon/CPolygon/Group/Previous/AUto\n\n;; Allow the user to only pick a single object\n(ssget \"_:S+.\")\n\nSelect objects: ?\n*Invalid selection*\nExpects a single object.\n\n;; Allow the user to only pick a single object or\n;; use the Last or Previous selection modes\n(ssget \"_:S+L+P\")\n\nSelect objects: ?\n*Invalid selection*\nValid keywords: Last/Previous\n\n;; Remove the Multiple and All selection modes\n(ssget \"-M-A\")\n\nSelect objects: ?\n*Invalid selection*\nExpects a point or Window/Last/Crossing/BOX/Fence/WPolygon/CPolygon/Group/Add/Remove/Previous/Undo/AUto/SIngle")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Selection Set Manipulation"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Creates a selection set from the selected object")

(setq *autolisp-reference-entry* (cons (cons 'summary *autolisp-reference-value*) *autolisp-reference-entry*))

(setq *autolisp-reference-value* "ssget (AutoLISP)")

(setq *autolisp-reference-entry* (cons (cons 'title *autolisp-reference-value*) *autolisp-reference-entry*))

(setq *autolisp-reference-value* "ssget")

(setq *autolisp-reference-entry* (cons (cons 'name *autolisp-reference-value*) *autolisp-reference-entry*))

(setq *autolisp-reference-parts* (cons (list (cons "ssget" *autolisp-reference-entry*)) *autolisp-reference-parts*))

(setq *autolisp-reference-parts*
  (cons
    '(("ssgetfirst" .
          ((name . "ssgetfirst")
           (title . "ssgetfirst (AutoLISP)")
           (summary . "Determines which objects are selected and gripped")
           (source-kind . "AutoLISP")
           (alphabetic-group . "S")
           (feature-groups . ("Selection Set Manipulation"))
           (supported-platforms . "Windows and Mac OS")
           (signature . "(ssgetfirst)")
           (arguments . nil)
           (return-values . "Type: List or nil\nReturns a list of two selection sets similar to those passed to sssetfirst. The first element in the list is always nil because AutoCAD no longer supports grips on unselected objects. The second element is a selection set of entities that are selected and gripped. Both elements of the list can be nil.")
           (release-information . nil)
           (history . nil)
           (examples . "N/A")
           (url . "https://help.autodesk.com/cloudhelp/2023/ENU/AutoCAD-AutoLISP-Reference/files/GUID-F18CB64C-1B18-46F3-BAD4-24D83214CE0D.htm")
           (guid . "GUID-F18CB64C-1B18-46F3-BAD4-24D83214CE0D"))))
    *autolisp-reference-parts*))

(setq *autolisp-reference-parts*
  (cons
    '(("sslength" .
          ((name . "sslength")
           (title . "sslength (AutoLISP)")
           (summary . "Returns an integer containing the number of objects (entities) in a selection set")
           (source-kind . "AutoLISP")
           (alphabetic-group . "S")
           (feature-groups . ("Selection Set Manipulation"))
           (supported-platforms . "Windows and Mac OS")
           (signature . "(sslength ss)")
           (arguments . (("ss" . "Type: Pickset (selection set)\nA selection set.")))
           (return-values . "Type: Integer\nThe number of objects in the selection set.")
           (release-information . nil)
           (history . nil)
           (examples . "Add the last object to a new selection set:\n\n(setq sset (ssget \"L\"))\n<Selection set: 8>\n\nUse sslength to determine the number of objects in the new selection set:\n\n(sslength sset)\n1")
           (url . "https://help.autodesk.com/cloudhelp/2023/ENU/AutoCAD-AutoLISP-Reference/files/GUID-034B9EC8-0945-48A0-802A-9725DDBA0EF2.htm")
           (guid . "GUID-034B9EC8-0945-48A0-802A-9725DDBA0EF2"))))
    *autolisp-reference-parts*))

(setq *autolisp-reference-parts*
  (cons
    '(("ssmemb" .
          ((name . "ssmemb")
           (title . "ssmemb (AutoLISP)")
           (summary . "Tests whether an object (entity) is a member of a selection set")
           (source-kind . "AutoLISP")
           (alphabetic-group . "S")
           (feature-groups . ("Selection Set Manipulation"))
           (supported-platforms . "Windows and Mac OS")
           (signature . "(ssmemb ename ss)")
           (arguments . (("ename" . "Type: Ename (entity name)\nAn entity name.")
                           ("ss" . "Type: Pickset (selection set)\nA selection set.")))
           (return-values . "Type: Ename (entity name) or nil\nIf ename is a member of ss, ssmemb returns the entity name. If ename is not a member, ssmemb returns nil.")
           (release-information . nil)
           (history . nil)
           (examples . "In the following examples, entity name e2 is a member of selection set ss, while entity name e1 is not a member of ss:\n\n(ssmemb e2 ss)\n<Entity name: 1d62d68>\n\n(ssmemb e1 ss)\nnil")
           (url . "https://help.autodesk.com/cloudhelp/2023/ENU/AutoCAD-AutoLISP-Reference/files/GUID-8F291146-6A1A-4A31-9380-C800590BF27D.htm")
           (guid . "GUID-8F291146-6A1A-4A31-9380-C800590BF27D"))))
    *autolisp-reference-parts*))

(setq *autolisp-reference-parts*
  (cons
    '(("ssname" .
          ((name . "ssname")
           (title . "ssname (AutoLISP)")
           (summary . "Returns the object (entity) name of the indexed element of a selection set")
           (source-kind . "AutoLISP")
           (alphabetic-group . "S")
           (feature-groups . ("Selection Set Manipulation"))
           (supported-platforms . "Windows and Mac OS")
           (signature . "(ssname ss index)")
           (arguments . (("ss" . "Type: Pickset (selection set)\nA selection set.")
                           ("index" . "Type: Integer or Real\nElement in a selection set. The first element in the set has an index of zero. To access entities beyond number 32,767 in a selection set, you must supply the index argument as a real.")))
           (return-values . "Type: Ename (entity name) or nil\nAn entity name, if successful. If index is negative or greater than the highest-numbered entity in the selection set, ssname returns nil.")
           (release-information . nil)
           (history . nil)
           (examples . "Get the name of the first entity in a selection set:\n\n(setq ent1 (ssname ss 0))\n<Entity name: 1d62d68>\n\nGet the name of the fourth entity in a selection set:\n\n(setq ent4 (ssname ss 3))\n<Entity name: 1d62d90>\n\nTo access entities beyond the number 32,767 in a selection set, you must supply the index argument as a real, as in the following example:\n\n(setq entx (ssname sset 50843.0))")
           (url . "https://help.autodesk.com/cloudhelp/2023/ENU/AutoCAD-AutoLISP-Reference/files/GUID-EFB83751-9AC5-4C52-AD3D-D971BC560C15.htm")
           (guid . "GUID-EFB83751-9AC5-4C52-AD3D-D971BC560C15"))))
    *autolisp-reference-parts*))

(setq *autolisp-reference-entry* nil)

(setq *autolisp-reference-value* "GUID-0A0E41A1-8F97-4B2E-A6A6-FF6223C6E999")

(setq *autolisp-reference-entry* (cons (cons 'guid *autolisp-reference-value*) *autolisp-reference-entry*))

(setq *autolisp-reference-value* "https://help.autodesk.com/cloudhelp/2023/ENU/AutoCAD-AutoLISP-Reference/files/GUID-0A0E41A1-8F97-4B2E-A6A6-FF6223C6E999.htm")

(setq *autolisp-reference-entry* (cons (cons 'url *autolisp-reference-value*) *autolisp-reference-entry*))

(setq *autolisp-reference-value* "The data associated with Pick (type 1) entity selections is a single point description. For example, the following record is returned for the selection of an entity picked at 1,1 in plan view of the WCS:\n\nCommand: (ssnamex ss3 0)\n\n((1 <Entity name: 1d62da0> 0 (0 (1.0 1.0 0.0))))\n\nThe data associated with an entity selected with the Window, WPolygon, Crossing, or CPolygon method is the integer ID of the polygon that selected the entity. It is up to the application to associate the polygon identifiers and make the connection between the polygon and the entities it selected. For example, the following returns an entity selected by Crossing (note that the polygon ID is -1):\n\nCommand: (ssnamex ss4 0)\n\n((3 <Entity name: 1d62d60> 0 -1) (-1 (0 (-1.80879 8.85536 0.0)) (0 (13.4004 8.85536 0.0))\n(0 (13.4004 1.80024 0.0)) (0 (-1.80879 1.80024 0.0))))\n\nThe data associated with fence sele")

(setq *autolisp-reference-value* (strcat *autolisp-reference-value* "ctions is a list of points and descriptions for the points where the fence and entity visually intersect. For example, the following command returns information for a nearly vertical line intersected three times by a Z-shaped fence:\n\nCommand: (ssnamex ss5 0)\n\n((4 <Entity name: 1d62d88> 0 (0 (5.28135 6.25219 0.0)) (0 (5.61868 2.81961 0.0))\n(0 (5.52688 3.75381 0.0))))"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* nil)

(setq *autolisp-reference-entry* (cons (cons 'return-values *autolisp-reference-value*) *autolisp-reference-entry*))

(setq *autolisp-reference-value* nil)

(setq *autolisp-reference-string* "Type: Integer or Real\nElement in a selection set. The first element in the set has an index of zero.")

(setq *autolisp-reference-value* (cons (cons "index" *autolisp-reference-string*) *autolisp-reference-value*))

(setq *autolisp-reference-string* "Type: Pickset (selection set)\nA selection set.")

(setq *autolisp-reference-value* (cons (cons "ss" *autolisp-reference-string*) *autolisp-reference-value*))

(setq *autolisp-reference-entry* (cons (cons 'arguments *autolisp-reference-value*) *autolisp-reference-entry*))

(setq *autolisp-reference-value* "(ssnamex ss [index])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Selection Set Manipulation"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Retrieves information about how a selection set was created.")

(setq *autolisp-reference-entry* (cons (cons 'summary *autolisp-reference-value*) *autolisp-reference-entry*))

(setq *autolisp-reference-value* "ssnamex (AutoLISP)")

(setq *autolisp-reference-entry* (cons (cons 'title *autolisp-reference-value*) *autolisp-reference-entry*))

(setq *autolisp-reference-value* "ssnamex")

(setq *autolisp-reference-entry* (cons (cons 'name *autolisp-reference-value*) *autolisp-reference-entry*))

(setq *autolisp-reference-parts* (cons (list (cons "ssnamex" *autolisp-reference-entry*)) *autolisp-reference-parts*))

(setq *autolisp-reference-entry* nil)

(setq *autolisp-reference-value* "GUID-4076CD9D-1C66-4C73-ACC0-3A6CD0B0D2D8")

(setq *autolisp-reference-entry* (cons (cons 'guid *autolisp-reference-value*) *autolisp-reference-entry*))

(setq *autolisp-reference-value* "https://help.autodesk.com/cloudhelp/2023/ENU/AutoCAD-AutoLISP-Reference/files/GUID-4076CD9D-1C66-4C73-ACC0-3A6CD0B0D2D8.htm")

(setq *autolisp-reference-entry* (cons (cons 'url *autolisp-reference-value*) *autolisp-reference-entry*))

(setq *autolisp-reference-value* "First, draw a square and build three selection sets. Begin by drawing side 1 and creating a selection set to include the line drawn:\n\n(entmake (list (cons 0 \"line\") '(10 0.0 0.0 0.0)'(11 0.0 10.0 0.0)))\n((0 . \"line\") (10 0.0 0.0 0.0) (11 0.0 10.0 0.0))\n\n(setq pickset1 (ssget \"_l\"))\n<Selection set: a5>\n\nVariable pickset1 points to the selection set created.\n\nDraw side 2 and add it to the pickset1 selection set:\n\n(entmake (list (cons 0 \"line\") '(10 0.0 10.0 0.0)'(11 10.0 10.0 0.0)))\n((0 . \"line\") (10 0.0 10.0 0.0) (11 10.0 10.0 0.0))\n\n(ssadd (entlast) pickset1)\n<Selection set: a5>\n\nCreate another selection set to include only side 2:\n\n(setq 2onlyset (ssget \"_l\"))\n<Selection set: a8>\n\nDraw side 3 and add it to the pickset1 selection set:\n\n(entmake (list (cons 0 \"line\") '(10 10.0 10.0 0.0)'(11 10.0 0.0 0.0)))\n((0 . \"line\") (10 10.0 10.0 0.0) (11 10.0")

(setq *autolisp-reference-value* (strcat *autolisp-reference-value* " 0.0 0.0))\n\n(ssadd (entlast) pickset1)\n<Selection set: a5>\n\nCreate another selection and include side 3 in the selection set:\n\n(setq pickset2 (ssget \"_l\"))\n<Selection set: ab>\n\nVariable pickset2 points to the new selection set.\n\nDraw side 4 and add it to the pickset1 and pickset2 selection sets:\n\n(entmake (list (cons 0 \"line\") '(10 10.0 0.0 0.0)'(11 0.0 0.0 0.0)))\n((0 . \"line\") (10 10.0 0.0 0.0) (11 0.0 0.0 0.0))\n\n(ssadd (entlast) pickset1)\n<Selection set: a5>\n\n(ssadd (entlast) pickset2)\n<Selection set: ab>\n\nAt this point, pickset1 contains sides 1-4, pickset2 contains sides 3 and 4, and 2onlyset contains only side 2.\n\nTurn grip handles on and select all objects in pickset1:\n\n(sssetfirst nil pickset1)\n(nil <Selection set: a5>)\n\nTurn grip handles on and select all objects in pickset2:\n\n(sssetfirst nil pickset2)\n(nil <Selection set: ab>)\n\nTurn grip "))

(setq *autolisp-reference-value* (strcat *autolisp-reference-value* "handles on and select all objects in 2onlyset:\n\n(sssetfirst nil 2onlyset)\n(nil <Selection set: a8>)\n\nEach sssetfirst call replaces the gripped and selected selection set from the previous sssetfirst call."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nThe selection set or sets specified.")

(setq *autolisp-reference-entry* (cons (cons 'return-values *autolisp-reference-value*) *autolisp-reference-entry*))

(setq *autolisp-reference-value* nil)

(setq *autolisp-reference-string* "Type: Pickset (selection set)\nA selection set to be selected.")

(setq *autolisp-reference-value* (cons (cons "pickset" *autolisp-reference-string*) *autolisp-reference-value*))

(setq *autolisp-reference-string* "Type: nil\nAutoCAD no longer supports grips on unselected objects, so this argument is ignored. However, if gripset is nil and no pickset is specified, sssetfirst turns off the grip handles and selections it previously turned on.")

(setq *autolisp-reference-value* (cons (cons "gripset" *autolisp-reference-string*) *autolisp-reference-value*))

(setq *autolisp-reference-entry* (cons (cons 'arguments *autolisp-reference-value*) *autolisp-reference-entry*))

(setq *autolisp-reference-value* "(sssetfirst gripset [pickset])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Selection Set Manipulation"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Sets which objects are selected and gripped")

(setq *autolisp-reference-entry* (cons (cons 'summary *autolisp-reference-value*) *autolisp-reference-entry*))

(setq *autolisp-reference-value* "sssetfirst (AutoLISP)")

(setq *autolisp-reference-entry* (cons (cons 'title *autolisp-reference-value*) *autolisp-reference-entry*))

(setq *autolisp-reference-value* "sssetfirst")

(setq *autolisp-reference-entry* (cons (cons 'name *autolisp-reference-value*) *autolisp-reference-entry*))

(setq *autolisp-reference-parts* (cons (list (cons "sssetfirst" *autolisp-reference-entry*)) *autolisp-reference-parts*))

(setq *autolisp-reference-parts*
  (cons
    '(("start_dialog" .
          ((name . "start_dialog")
           (title . "start_dialog (AutoLISP/DCL)")
           (summary . "Displays a dialog box and begins accepting user input")
           (source-kind . "AutoLISP/DCL")
           (alphabetic-group . "S")
           (feature-groups . ("Dialog Box Opening and Closing Functions Reference (AutoLISP/DCL)"))
           (supported-platforms . "Windows and Mac OS")
           (signature . "(start_dialog)")
           (arguments . nil)
           (return-values . "Type: Integer\nThe start_dialog function returns the optional status passed to done_dialog. The default value is 1 if the user presses OK, 0 if the user presses Cancel, or -1 if all dialog boxes are terminated with term_dialog. If done_dialog is passed an integer status greater than 1, start_dialog returns this value, whose meaning is determined by the application.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-E4432FB7-6549-4C9B-B5AF-4990050BDBE1.htm")
           (guid . "GUID-E4432FB7-6549-4C9B-B5AF-4990050BDBE1"))))
    *autolisp-reference-parts*))

(setq *autolisp-reference-parts*
  (cons
    '(("start_image" .
          ((name . "start_image")
           (title . "start_image (AutoLISP/DCL)")
           (summary . "Starts the creation of an image in the dialog box tile")
           (source-kind . "AutoLISP/DCL")
           (alphabetic-group . "S")
           (feature-groups . ("Image Tile-Handling Functions Reference (AutoLISP/DCL)"))
           (supported-platforms . "Windows and Mac OS")
           (signature . "(start_image key)")
           (arguments . (("key" . "Type: String\nValue that specifies a tile. This argument is case-sensitive.")))
           (return-values . "Type: String or nil\nThe key argument, if successful; otherwise nil.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-4CB5C93A-6357-4853-B918-0F3EE375201C.htm")
           (guid . "GUID-4CB5C93A-6357-4853-B918-0F3EE375201C"))))
    *autolisp-reference-parts*))

(setq *autolisp-reference-parts*
  (cons
    '(("start_list" .
          ((name . "start_list")
           (title . "start_list (AutoLISP/DCL)")
           (summary . "Starts the processing of a list in the list box or in the pop-up list dialog box tile")
           (source-kind . "AutoLISP/DCL")
           (alphabetic-group . "S")
           (feature-groups . ("List Box and Pop-Up List-Handling Functions Reference (AutoLISP/DCL)"))
           (supported-platforms . "Windows and Mac OS")
           (signature . "(start_list key [operation [index]])")
           (arguments . (("key" . "Type: String\nValue that specifies a tile. This argument is case-sensitive.")
                           ("operation" . "Type: Integer\nA numeric value indicating the type of list operation to perform. You can specify one of the following:\n1 -- Change selected list contents\n2 -- Append new list entry\n3 -- Delete old list and create new list (the default)")
                           ("index" . "Type: Integer\nA number indicating the list item to change by the subsequent add_list call. The first item in the list is index 0. If not specified, index defaults to 0.\nThe index argument is ignored if start_list is not performing a change operation.")))
           (return-values . "Type: String\nThe name of the list that was started.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-84FAC8F6-59B1-4FBD-9446-0CB323B3D66D.htm")
           (guid . "GUID-84FAC8F6-59B1-4FBD-9446-0CB323B3D66D"))))
    *autolisp-reference-parts*))

(setq *autolisp-reference-entry* nil)

(setq *autolisp-reference-value* "GUID-30EC493A-674B-4AAE-8C88-358E38CDAB21")

(setq *autolisp-reference-entry* (cons (cons 'guid *autolisp-reference-value*) *autolisp-reference-entry*))

(setq *autolisp-reference-value* "https://help.autodesk.com/cloudhelp/2023/ENU/AutoCAD-AutoLISP-Reference/files/GUID-30EC493A-674B-4AAE-8C88-358E38CDAB21.htm")

(setq *autolisp-reference-entry* (cons (cons 'url *autolisp-reference-value*) *autolisp-reference-entry*))

(setq *autolisp-reference-value* "Windows\n\nThe following code starts Notepad and opens the acad.lsp file.\n(startapp \"notepad\" \"acad.lsp\")\n33\nIf an argument has embedded spaces, it must be surrounded by literal double quotes. For example, to edit the file my stuff.txt with Notepad, use the following syntax:\n(startapp \"notepad.exe\" \"\\\"my stuff.txt\\\"\")\n33\n\nMac OS\n\nThe following code starts TextEdit and opens the acad.lsp file.\n(startapp \"textedit\" \"acad.lsp\")\n33\nIf an argument has embedded spaces, it must be surrounded by literal double quotes. For example, to edit the file my stuff.txt with TextEdit, use the following syntax:\n(startapp \"textedit.app\" \"\\\"my stuff.txt\\\"\")\n33")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer or nil\nA numeric value greater than 0, if successful; otherwise nil.")

(setq *autolisp-reference-entry* (cons (cons 'return-values *autolisp-reference-value*) *autolisp-reference-entry*))

(setq *autolisp-reference-value* nil)

(setq *autolisp-reference-string* "Type: String\nFile name to be opened.")

(setq *autolisp-reference-value* (cons (cons "file" *autolisp-reference-string*) *autolisp-reference-value*))

(setq *autolisp-reference-string* "Type: String\nApplication to execute. If appcmd does not include a full path name, startapp searches the directories in the PATH environment variable on Windows for the application and the equivalent on Mac OS.")

(setq *autolisp-reference-value* (cons (cons "appcmd" *autolisp-reference-string*) *autolisp-reference-value*))

(setq *autolisp-reference-entry* (cons (cons 'arguments *autolisp-reference-value*) *autolisp-reference-entry*))

(setq *autolisp-reference-value* "(startapp appcmd [file])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Application-Handling"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Starts an external application")

(setq *autolisp-reference-entry* (cons (cons 'summary *autolisp-reference-value*) *autolisp-reference-entry*))

(setq *autolisp-reference-value* "startapp (AutoLISP)")

(setq *autolisp-reference-entry* (cons (cons 'title *autolisp-reference-value*) *autolisp-reference-entry*))

(setq *autolisp-reference-value* "startapp")

(setq *autolisp-reference-entry* (cons (cons 'name *autolisp-reference-value*) *autolisp-reference-entry*))

(setq *autolisp-reference-parts* (cons (list (cons "startapp" *autolisp-reference-entry*)) *autolisp-reference-parts*))

(setq *autolisp-reference-parts*
  (cons
    '(("strcase" .
          ((name . "strcase")
           (title . "strcase (AutoLISP)")
           (summary . "Returns a string where all alphabetic characters have been converted to uppercase or lowercase")
           (source-kind . "AutoLISP")
           (alphabetic-group . "S")
           (feature-groups . ("String-Handling"))
           (supported-platforms . "Windows and Mac OS")
           (signature . "(strcase string [which])")
           (arguments . (("string" . "Type: String\nThe text string to convert.")
                           ("which" . "Type: T or nil\nIf specified as T, all alphabetic characters in string are converted to lowercase. Otherwise, characters are converted to uppercase.")))
           (return-values . "Type: String\nConverted text value.")
           (release-information . nil)
           (history . nil)
           (examples . "(strcase \"Sample\")\n\"SAMPLE\"\n\n(strcase \"Sample\" T)\n\"sample\"\n\nThe strcase function will correctly handle case mapping of the currently configured character set.")
           (url . "https://help.autodesk.com/cloudhelp/2023/ENU/AutoCAD-AutoLISP-Reference/files/GUID-108DCD2C-6597-4548-856D-937787AFE5E0.htm")
           (guid . "GUID-108DCD2C-6597-4548-856D-937787AFE5E0"))))
    *autolisp-reference-parts*))

(setq *autolisp-reference-parts*
  (cons
    '(("strcat" .
          ((name . "strcat")
           (title . "strcat (AutoLISP)")
           (summary . "Returns a string that is the concatenation of multiple strings")
           (source-kind . "AutoLISP")
           (alphabetic-group . "S")
           (feature-groups . ("String-Handling"))
           (supported-platforms . "Windows and Mac OS")
           (signature . "(strcat [string string_n ...])")
           (arguments . (("string" . "Type: String\nText values to concatenate.")))
           (return-values . "Type: String\nConcatenate text string. If no arguments are supplied, strcat returns a zero-length string.")
           (release-information . nil)
           (history . nil)
           (examples . "(strcat \"a\" \"bout\")\n\"about\"\n\n(strcat \"a\" \"b\" \"c\")\n\"abc\"\n\n(strcat \"a\" \"\" \"c\")\n\"ac\"\n\n(strcat)\n\"\"")
           (url . "https://help.autodesk.com/cloudhelp/2023/ENU/AutoCAD-AutoLISP-Reference/files/GUID-4430B1BF-DBB5-49D1-98F9-711B480976A1.htm")
           (guid . "GUID-4430B1BF-DBB5-49D1-98F9-711B480976A1"))))
    *autolisp-reference-parts*))

(setq *autolisp-reference-entry* nil)

(setq *autolisp-reference-value* "GUID-F16AAC5F-5C87-4DC5-A7B9-BDCD25DC507A")

(setq *autolisp-reference-entry* (cons (cons 'guid *autolisp-reference-value*) *autolisp-reference-entry*))

(setq *autolisp-reference-value* "https://help.autodesk.com/cloudhelp/2023/ENU/AutoCAD-AutoLISP-Reference/files/GUID-F16AAC5F-5C87-4DC5-A7B9-BDCD25DC507A.htm")

(setq *autolisp-reference-entry* (cons (cons 'url *autolisp-reference-value*) *autolisp-reference-entry*))

(setq *autolisp-reference-value* "(strlen \"abcd\")\n4\n\n(strlen \"ab\")\n2\n\n(strlen \"one\" \"two\" \"four\")\n10\n\n(strlen \"中\")\n1\n\n(strlen \"测试\")\n2\n\n(strlen)\n0\n\n(strlen \"\")\n0")

(setq *autolisp-reference-entry* (cons (cons 'examples *autolisp-reference-value*) *autolisp-reference-entry*))

(setq *autolisp-reference-value* "AutoCAD 2021\n- str\n- argument previously accepted an ASCII text string or character, but now accepts a Unicode text string or character.\n- Return value was modified to support Unicode characters and might be different than earlier releases. In earlier releases, the length of a Unicode character was improperly calculated. For example,\n- (strlen \"中国\")\n- previously returned 14, but now returns 2.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: Integer\nA numeric value. If multiple str arguments are provided, strlen returns the sum of the lengths of all arguments. If you omit the arguments or enter an empty string, strlen returns 0.")

(setq *autolisp-reference-entry* (cons (cons 'return-values *autolisp-reference-value*) *autolisp-reference-entry*))

(setq *autolisp-reference-value* nil)

(setq *autolisp-reference-string* "Type: String\nA textual value.")

(setq *autolisp-reference-value* (cons (cons "str" *autolisp-reference-string*) *autolisp-reference-value*))

(setq *autolisp-reference-entry* (cons (cons 'arguments *autolisp-reference-value*) *autolisp-reference-entry*))

(setq *autolisp-reference-value* "(strlen [str ...])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns an integer that is the number of characters in a string")

(setq *autolisp-reference-entry* (cons (cons 'summary *autolisp-reference-value*) *autolisp-reference-entry*))

(setq *autolisp-reference-value* "strlen (AutoLISP)")

(setq *autolisp-reference-entry* (cons (cons 'title *autolisp-reference-value*) *autolisp-reference-entry*))

(setq *autolisp-reference-value* "strlen")

(setq *autolisp-reference-entry* (cons (cons 'name *autolisp-reference-value*) *autolisp-reference-entry*))

(setq *autolisp-reference-parts* (cons (list (cons "strlen" *autolisp-reference-entry*)) *autolisp-reference-parts*))

(setq *autolisp-reference-entry* nil)

(setq *autolisp-reference-value* "GUID-25214E69-090A-45C3-8210-6D9801255E44")

(setq *autolisp-reference-entry* (cons (cons 'guid *autolisp-reference-value*) *autolisp-reference-entry*))

(setq *autolisp-reference-value* "https://help.autodesk.com/cloudhelp/2023/ENU/AutoCAD-AutoLISP-Reference/files/GUID-25214E69-090A-45C3-8210-6D9801255E44.htm")

(setq *autolisp-reference-entry* (cons (cons 'url *autolisp-reference-value*) *autolisp-reference-entry*))

(setq *autolisp-reference-value* "(setq sample '(a b (c d) b))\n(A B (C D) B)\n\n(subst 'qq 'b sample)\n(A QQ (C D) QQ)\n\n(subst 'qq 'z sample)\n(A B (C D) B)\n\n(subst 'qq '(c d) sample)\n(A B QQ B)\n\n(subst '(qq rr) '(c d) sample)\n(A B (QQ RR) B)\n\n(subst '(qq rr) 'z sample)\n(A B (C D) B)\n\nWhen used in conjunction with assoc, subst provides a convenient means of replacing the value associated with one key in an association list, as demonstrated by the following function calls.\n\nSet variable who to an association list:\n\n(setq who '((first john) (mid q) (last public)))\n((FIRST JOHN) (MID Q) (LAST PUBLIC))\n\nThe following sets old to (FIRST JOHN) and new to (FIRST J):\n\n(setq old (assoc 'first who) new '(first j))\n(FIRST J)\n\nFinally, replace the value of the first item in the association list:\n\n(subst new old who)\n((FIRST J) (MID Q) (LAST PUBLIC))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "A list, with newitem replacing all occurrences of olditem. If olditem is not found in lst, subst returns lst unchanged.")

(setq *autolisp-reference-entry* (cons (cons 'return-values *autolisp-reference-value*) *autolisp-reference-entry*))

(setq *autolisp-reference-value* nil)

(setq *autolisp-reference-string* "Type: List\nA list.")

(setq *autolisp-reference-value* (cons (cons "lst" *autolisp-reference-string*) *autolisp-reference-value*))

(setq *autolisp-reference-string* "Type: Integer, Real, String, List, Symbol, Ename (entity name), T, or nil\nAn atom or list.")

(setq *autolisp-reference-value* (cons (cons "olditem" *autolisp-reference-string*) *autolisp-reference-value*))

(setq *autolisp-reference-string* "Type: Integer, Real, String, List, Symbol, Ename (entity name), T, or nil\nAn atom or list.")

(setq *autolisp-reference-value* (cons (cons "newitem" *autolisp-reference-string*) *autolisp-reference-value*))

(setq *autolisp-reference-entry* (cons (cons 'arguments *autolisp-reference-value*) *autolisp-reference-entry*))

(setq *autolisp-reference-value* "(subst newitem olditem lst)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("List Manipulation"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Searches a list for an old item and returns a copy of the list with a new item substituted in place of every occurrence of the old item")

(setq *autolisp-reference-entry* (cons (cons 'summary *autolisp-reference-value*) *autolisp-reference-entry*))

(setq *autolisp-reference-value* "subst (AutoLISP)")

(setq *autolisp-reference-entry* (cons (cons 'title *autolisp-reference-value*) *autolisp-reference-entry*))

(setq *autolisp-reference-value* "subst")

(setq *autolisp-reference-entry* (cons (cons 'name *autolisp-reference-value*) *autolisp-reference-entry*))

(setq *autolisp-reference-parts* (cons (list (cons "subst" *autolisp-reference-entry*)) *autolisp-reference-parts*))

(setq *autolisp-reference-entry* nil)

(setq *autolisp-reference-value* "GUID-36F8701B-7AB7-47BE-AC31-8508A2DF46A2")

(setq *autolisp-reference-entry* (cons (cons 'guid *autolisp-reference-value*) *autolisp-reference-entry*))

(setq *autolisp-reference-value* "https://help.autodesk.com/cloudhelp/2023/ENU/AutoCAD-AutoLISP-Reference/files/GUID-36F8701B-7AB7-47BE-AC31-8508A2DF46A2.htm")

(setq *autolisp-reference-entry* (cons (cons 'url *autolisp-reference-value*) *autolisp-reference-entry*))

(setq *autolisp-reference-value* nil)

(setq *autolisp-reference-entry* (cons (cons 'examples *autolisp-reference-value*) *autolisp-reference-entry*))

(setq *autolisp-reference-value* "AutoCAD 2021\n- str\n- argument previously accepted an ASCII text string or character, but now accepts a Unicode text string or character.\n- Return value was modified to support Unicode characters and might be different than earlier releases. In earlier releases, the length of a Unicode character was improperly calculated. For example,\n- (substr \"中国\" 1 1)\n- previously returned \"\\\\\", but now returns \"中\".\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: String\nA substring from str.")

(setq *autolisp-reference-entry* (cons (cons 'return-values *autolisp-reference-value*) *autolisp-reference-entry*))

(setq *autolisp-reference-value* nil)

(setq *autolisp-reference-string* "Type: Integer\nA positive numeric value specifying the number of characters to search through in str. If length is not specified, the substring continues to the end of str.")

(setq *autolisp-reference-value* (cons (cons "length" *autolisp-reference-string*) *autolisp-reference-value*))

(setq *autolisp-reference-string* "Type: Integer\nA positive numeric value indicating the starting position in str. The first character in the string is position 1.")

(setq *autolisp-reference-value* (cons (cons "start" *autolisp-reference-string*) *autolisp-reference-value*))

(setq *autolisp-reference-string* "Type: String\nA textual value.")

(setq *autolisp-reference-value* (cons (cons "str" *autolisp-reference-string*) *autolisp-reference-value*))

(setq *autolisp-reference-entry* (cons (cons 'arguments *autolisp-reference-value*) *autolisp-reference-entry*))

(setq *autolisp-reference-value* "(substr str start [length])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "S")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns a substring of a string")

(setq *autolisp-reference-entry* (cons (cons 'summary *autolisp-reference-value*) *autolisp-reference-entry*))

(setq *autolisp-reference-value* "substr (AutoLISP)")

(setq *autolisp-reference-entry* (cons (cons 'title *autolisp-reference-value*) *autolisp-reference-entry*))

(setq *autolisp-reference-value* "substr")

(setq *autolisp-reference-entry* (cons (cons 'name *autolisp-reference-value*) *autolisp-reference-entry*))

(setq *autolisp-reference-parts* (cons (list (cons "substr" *autolisp-reference-entry*)) *autolisp-reference-parts*))

(setq *autolisp-reference-entry* nil)

(setq *autolisp-reference-value* "GUID-5AD61389-1F8E-497B-8B0B-259488A50772")

(setq *autolisp-reference-entry* (cons (cons 'guid *autolisp-reference-value*) *autolisp-reference-entry*))

(setq *autolisp-reference-value* "https://help.autodesk.com/cloudhelp/2023/ENU/AutoCAD-AutoLISP-Reference/files/GUID-5AD61389-1F8E-497B-8B0B-259488A50772.htm")

(setq *autolisp-reference-entry* (cons (cons 'url *autolisp-reference-value*) *autolisp-reference-entry*))

(setq *autolisp-reference-value* "A very simple transformation that can be established with tablet is the identity transformation:\n\n(tablet 1 '(1 0 0) '(0 1 0) '(0 0 1) '(0 0 1))\n\nWith this transformation in effect, AutoCAD will receive, effectively, raw digitizer coordinates from the tablet. For example, if you pick the point with digitizer coordinates (5000,15000), AutoCAD will see it as the point in your drawing with those same coordinates.\n\nThe AutoCAD TABMODE system variable allows AutoLISP routines to toggle the tablet on and off.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer or nil\nIf tablet fails, it returns nil and sets the AutoCAD ERRNO system variable to a value that indicates the reason for the failure. This can happen if the digitizer is not a tablet.")

(setq *autolisp-reference-entry* (cons (cons 'return-values *autolisp-reference-value*) *autolisp-reference-entry*))

(setq *autolisp-reference-value* nil)

(setq *autolisp-reference-string* "Type: List\nOne 3D point. This is the vector (expressed in the world coordinate system, or WCS) that is normal to the plane that represents the surface of the tablet.\nIf the specified direction isn't normalized, tablet corrects it, so the direction it returns when you set the calibration may differ from the value you passed.")

(setq *autolisp-reference-value* (cons (cons "direction" *autolisp-reference-string*) *autolisp-reference-value*))

(setq *autolisp-reference-string* "Type: List\nThree 3D points. These three arguments specify the three rows of the tablet's transformation matrix.\nThe third element in row3 (Z) should always equal 1: tablet returns it as 1 even if you specify a different value in row3.")

(setq *autolisp-reference-value* (cons (cons "row1, row2, row3" *autolisp-reference-string*) *autolisp-reference-value*))

(setq *autolisp-reference-string* "Type: Integer\nOne of the following:\n0 -- Return the current digitizer calibration. In this case, the remaining arguments must be omitted.\n1 -- Set the calibration according to the arguments that follow. In this case, you must provide the new calibration settings (row1,row2,row3, and direction).")

(setq *autolisp-reference-value* (cons (cons "code" *autolisp-reference-string*) *autolisp-reference-value*))

(setq *autolisp-reference-entry* (cons (cons 'arguments *autolisp-reference-value*) *autolisp-reference-entry*))

(setq *autolisp-reference-value* "(tablet code [row1 row2 row3 direction])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Device Access"))

(setq *autolisp-reference-entry* (cons (cons 'feature-groups *autolisp-reference-value*) *autolisp-reference-entry*))

(setq *autolisp-reference-value* "T")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Retrieves and sets digitizer (tablet) calibrations")

(setq *autolisp-reference-entry* (cons (cons 'summary *autolisp-reference-value*) *autolisp-reference-entry*))

(setq *autolisp-reference-value* "tablet (AutoLISP)")

(setq *autolisp-reference-entry* (cons (cons 'title *autolisp-reference-value*) *autolisp-reference-entry*))

(setq *autolisp-reference-value* "tablet")

(setq *autolisp-reference-entry* (cons (cons 'name *autolisp-reference-value*) *autolisp-reference-entry*))

(setq *autolisp-reference-parts* (cons (list (cons "tablet" *autolisp-reference-entry*)) *autolisp-reference-parts*))

(setq *autolisp-reference-entry* nil)

(setq *autolisp-reference-value* "GUID-1720D8DC-5559-4AC1-8A75-3C932834D77C")

(setq *autolisp-reference-entry* (cons (cons 'guid *autolisp-reference-value*) *autolisp-reference-entry*))

(setq *autolisp-reference-value* "https://help.autodesk.com/cloudhelp/2023/ENU/AutoCAD-AutoLISP-Reference/files/GUID-1720D8DC-5559-4AC1-8A75-3C932834D77C.htm")

(setq *autolisp-reference-entry* (cons (cons 'url *autolisp-reference-value*) *autolisp-reference-entry*))

(setq *autolisp-reference-value* "Retrieve the first layer in the symbol table:\n\n(tblnext \"layer\" T)\n((0 . \"LAYER\") (2 . \"0\") (70 . 0) (62 . 7) (6 . \"CONTINUOUS\"))\n\nThe return values represent the following:\n\n(0 . \"LAYER\")               Symbol type\n(2 . \"0\")                   Symbol name\n(70 . 0)                    Flags\n(62 . 7)                    Color number, negative if off\n(6 . \"CONTINUOUS\")          Linetype name\n\nNote that there is no -1 group. The last entry returned from each table is stored, and the next one is returned each time tblnext is called for that table. When you begin scanning a table, be sure to supply a non-nil second argument to rewind the table and to return the first entry.\n\nEntries retrieved from the block table include a -2 group with the entity name of the first entity in the block definition (if any). For example, the following command obtains information about a ")

(setq *autolisp-reference-value* (strcat *autolisp-reference-value* "block called BOX:\n\n(tblnext \"block\")\n((0 . \"BLOCK\") (2 . \"BOX\") (70 . 0) (10 9.0 2.0 0.0) (-2 . <Entity name: 1dca370>))\n\nThe return values represent the following:\n\n(0 . \"BLOCK\")                    Symbol type\n(2 . \"BOX\")                      Symbol name\n(70 . 0)                         Flags\n(10 9.0 2.0 0.0)                 Origin X,Y,Z\n(-2 . <Entity name: 1dca370>)    First entity\n\nThe entity name in the -2 group is accepted by entget and entnext, but not by other entity access functions. For example, you cannot use ssadd to put it in a selection set. By providing the -2 group entity name to entnext, you can scan the entities comprising a block definition; entnext returns nil after the last entity in the block definition.\n\nIf a block contains no entities, the -2 group returned by tblnext is the entity name of its endblk entity."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nIf a symbol table entry is found, the entry is returned as a list of dotted pairs of DXF-type codes and values. If there are no more entries in the table, nil is returned. Deleted table entries are never returned.")

(setq *autolisp-reference-entry* (cons (cons 'return-values *autolisp-reference-value*) *autolisp-reference-entry*))

(setq *autolisp-reference-value* nil)

(setq *autolisp-reference-string* "Type: T or nil\nIf this argument is present and is not nil, the symbol table is rewound and the first entry in it is retrieved.")

(setq *autolisp-reference-value* (cons (cons "rewind" *autolisp-reference-string*) *autolisp-reference-value*))

(setq *autolisp-reference-string* "Type: String\nSymbol table name.\nValid table-name values are:\n- \"APPID\"\n- \"BLOCK\"\n- \"DIMSTYLE\"\n- \"LAYER\"\n- \"LTYPE\"\n- \"STYLE\"\n- \"UCS\"\n- \"VIEW\"\n- \"VPORT\"\nThe argument is not case sensitive.")

(setq *autolisp-reference-value* (cons (cons "table-name" *autolisp-reference-string*) *autolisp-reference-value*))

(setq *autolisp-reference-entry* (cons (cons 'arguments *autolisp-reference-value*) *autolisp-reference-entry*))

(setq *autolisp-reference-value* "(tblnext table-name [rewind])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Symbol Table and Dictionary-Handling"))

(setq *autolisp-reference-entry* (cons (cons 'feature-groups *autolisp-reference-value*) *autolisp-reference-entry*))

(setq *autolisp-reference-value* "T")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Finds the next item in a symbol table")

(setq *autolisp-reference-entry* (cons (cons 'summary *autolisp-reference-value*) *autolisp-reference-entry*))

(setq *autolisp-reference-value* "tblnext (AutoLISP)")

(setq *autolisp-reference-entry* (cons (cons 'title *autolisp-reference-value*) *autolisp-reference-entry*))

(setq *autolisp-reference-value* "tblnext")

(setq *autolisp-reference-entry* (cons (cons 'name *autolisp-reference-value*) *autolisp-reference-entry*))

(setq *autolisp-reference-parts* (cons (list (cons "tblnext" *autolisp-reference-entry*)) *autolisp-reference-parts*))

(setq *autolisp-reference-parts*
  (cons
    '(("tblobjname" .
          ((name . "tblobjname")
           (title . "tblobjname (AutoLISP)")
           (summary . "Returns the entity name of a specified symbol table entry")
           (source-kind . "AutoLISP")
           (alphabetic-group . "T")
           (feature-groups . ("Symbol Table and Dictionary-Handling"))
           (supported-platforms . "Windows and Mac OS")
           (signature . "(tblobjname table-name symbol)")
           (arguments . (("table-name" . "Type: String\nSymbol table to be searched. The argument is not case-sensitive.")
                           ("symbol" . "Type: String\nSymbol to be searched for.")))
           (return-values . "Type: Ename (entity name) or nil\nThe entity name of the symbol table entry, if found.\nThe entity name returned by tblobjname can be used in entget and entmod operations.")
           (release-information . nil)
           (history . nil)
           (examples . "The following command searches for the entity name of the block entry “ESC-01”:\n\n(tblobjname \"block\" \"ESC-01\")\n<Entity name: 1dca368>")
           (url . "https://help.autodesk.com/cloudhelp/2023/ENU/AutoCAD-AutoLISP-Reference/files/GUID-B75D58C9-8ED9-4025-906A-76B243CD5D8D.htm")
           (guid . "GUID-B75D58C9-8ED9-4025-906A-76B243CD5D8D"))))
    *autolisp-reference-parts*))

(setq *autolisp-reference-parts*
  (cons
    '(("tblsearch" .
          ((name . "tblsearch")
           (title . "tblsearch (AutoLISP)")
           (summary . "Searches a symbol table for a symbol name")
           (source-kind . "AutoLISP")
           (alphabetic-group . "T")
           (feature-groups . ("Symbol Table and Dictionary-Handling"))
           (supported-platforms . "Windows and Mac OS")
           (signature . "(tblsearch table-name symbol [setnext])")
           (arguments . (("table-name" . "Type: String\nSymbol table to be searched. This argument is not case-sensitive.")
                           ("symbol" . "Type: String\nSymbol name to be searched for. This argument is not case-sensitive.")
                           ("setnext" . "Type: T or nil\nIf this argument is supplied and is not nil, the tblnext entry counter is adjusted so the following tblnext call returns the entry after the one returned by this tblsearch call. Otherwise, tblsearch has no effect on the order of entries retrieved by tblnext.")))
           (return-values . "Type: List (dotted pairs) or nil\nIf tblsearch finds an entry for the given symbol name, it returns that entry. If no entry is found, tblsearch returns nil.")
           (release-information . nil)
           (history . nil)
           (examples . "The following command searches for a text style named “standard”:\n\n(tblsearch \"style\" \"standard\")\n((0 . \"STYLE\") (2 . \"STANDARD\") (70 . 0) (40 . 0.0) (41 . 1.0) (50 . 0.0) (71 . 0) (42 . 0.3) (3 . \"txt\") (4 . \"\"))")
           (url . "https://help.autodesk.com/cloudhelp/2023/ENU/AutoCAD-AutoLISP-Reference/files/GUID-2AEB84A6-E3D0-4DD9-A29C-54D4099ED925.htm")
           (guid . "GUID-2AEB84A6-E3D0-4DD9-A29C-54D4099ED925"))))
    *autolisp-reference-parts*))

(setq *autolisp-reference-parts*
  (cons
    '(("term_dialog" .
          ((name . "term_dialog")
           (title . "term_dialog (AutoLISP/DCL)")
           (summary . "Terminates all current dialog boxes as if the user had canceled each of them")
           (source-kind . "AutoLISP/DCL")
           (alphabetic-group . "T")
           (feature-groups . ("Dialog Box Opening and Closing Functions Reference (AutoLISP/DCL)"))
           (supported-platforms . "Windows and Mac OS")
           (signature . "(term_dialog)")
           (arguments . nil)
           (return-values . "Type: nil\nAlways returns nil.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-7276E779-2FBA-47A5-AF3D-36927B738671.htm")
           (guid . "GUID-7276E779-2FBA-47A5-AF3D-36927B738671"))))
    *autolisp-reference-parts*))

(setq *autolisp-reference-parts*
  (cons
    '(("terpri" .
          ((name . "terpri")
           (title . "terpri (AutoLISP)")
           (summary . "Prints a newline to the command line")
           (source-kind . "AutoLISP")
           (alphabetic-group . "T")
           (feature-groups . ("Display Control"))
           (supported-platforms . "Windows and Mac OS")
           (signature . "(terpri)")
           (arguments . nil)
           (return-values . "Type: nil\nAlways returns nil.")
           (release-information . nil)
           (history . nil)
           (examples . "N/A")
           (url . "https://help.autodesk.com/cloudhelp/2023/ENU/AutoCAD-AutoLISP-Reference/files/GUID-16FB5411-7563-4FB9-AB59-A73457B092C5.htm")
           (guid . "GUID-16FB5411-7563-4FB9-AB59-A73457B092C5"))))
    *autolisp-reference-parts*))

(setq *autolisp-reference-entry* nil)

(setq *autolisp-reference-value* "GUID-D6C31C79-ECBF-4C7D-9285-1CFA95AC0918")

(setq *autolisp-reference-entry* (cons (cons 'guid *autolisp-reference-value*) *autolisp-reference-entry*))

(setq *autolisp-reference-value* "https://help.autodesk.com/cloudhelp/2023/ENU/AutoCAD-AutoLISP-Reference/files/GUID-D6C31C79-ECBF-4C7D-9285-1CFA95AC0918.htm")

(setq *autolisp-reference-entry* (cons (cons 'url *autolisp-reference-value*) *autolisp-reference-entry*))

(setq *autolisp-reference-value* "The following command supplies the text and accepts the current defaults for the remaining parameters:\n\n(textbox '((1 . \"Hello world.\")))\n((0.000124126 -0.00823364 0.0) (3.03623 0.310345 0.0))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nA list of two points, if successful; otherwise nil.\nThe points returned by textbox describe the bounding box of the text object as if its insertion point is located at (0,0,0) and its rotation angle is 0. The first list returned is generally the point (0.0 0.0 0.0) unless the text object is oblique or vertical, or it contains letters with descenders (such as g and p). The value of the first point list specifies the offset from the text insertion point to the lower-left corner of the smallest rectangle enclosing the text. The second point list specifies the upper-right corner of that box. Regardless of the orientation of the text being measured, the point list returned always describes the lower-left and upper-right corners of this bounding box.")

(setq *autolisp-reference-entry* (cons (cons 'return-values *autolisp-reference-value*) *autolisp-reference-entry*))

(setq *autolisp-reference-value* nil)

(setq *autolisp-reference-string* "Type: List\nAn entity definition list defining a text object, in the format returned by entget.\nIf fields that define text parameters other than the text itself are omitted from elist, the current (or default) settings are used.\nThe minimum list accepted by textbox is that of the text itself.")

(setq *autolisp-reference-value* (cons (cons "elist" *autolisp-reference-string*) *autolisp-reference-value*))

(setq *autolisp-reference-entry* (cons (cons 'arguments *autolisp-reference-value*) *autolisp-reference-entry*))

(setq *autolisp-reference-value* "(textbox elist)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Geometric"))

(setq *autolisp-reference-entry* (cons (cons 'feature-groups *autolisp-reference-value*) *autolisp-reference-entry*))

(setq *autolisp-reference-value* "T")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Measures a specified text object, and returns the diagonal coordinates of a box that encloses the text")

(setq *autolisp-reference-entry* (cons (cons 'summary *autolisp-reference-value*) *autolisp-reference-entry*))

(setq *autolisp-reference-value* "textbox (AutoLISP)")

(setq *autolisp-reference-entry* (cons (cons 'title *autolisp-reference-value*) *autolisp-reference-entry*))

(setq *autolisp-reference-value* "textbox")

(setq *autolisp-reference-entry* (cons (cons 'name *autolisp-reference-value*) *autolisp-reference-entry*))

(setq *autolisp-reference-parts* (cons (list (cons "textbox" *autolisp-reference-entry*)) *autolisp-reference-parts*))

(setq *autolisp-reference-parts*
  (cons
    '(("textpage" .
          ((name . "textpage")
           (title . "textpage (AutoLISP)")
           (summary . "Switches focus from the drawing area to the text screen")
           (source-kind . "AutoLISP")
           (alphabetic-group . "T")
           (feature-groups . ("Display Control"))
           (supported-platforms . "Windows and Mac OS")
           (signature . "(textpage)")
           (arguments . nil)
           (return-values . "Type: nil\nAlways returns nil.")
           (release-information . nil)
           (history . nil)
           (examples . "N/A")
           (url . "https://help.autodesk.com/cloudhelp/2023/ENU/AutoCAD-AutoLISP-Reference/files/GUID-C5F1E0AF-CAE8-4338-8C27-5A4235D37145.htm")
           (guid . "GUID-C5F1E0AF-CAE8-4338-8C27-5A4235D37145"))))
    *autolisp-reference-parts*))

(setq *autolisp-reference-parts*
  (cons
    '(("textscr" .
          ((name . "textscr")
           (title . "textscr (AutoLISP)")
           (summary . "Switches focus from the drawing area to the text screen")
           (source-kind . "AutoLISP")
           (alphabetic-group . "T")
           (feature-groups . ("Display Control"))
           (supported-platforms . "Windows and Mac OS")
           (signature . "(textscr)")
           (arguments . nil)
           (return-values . "Type: nil\nAlways returns nil.")
           (release-information . nil)
           (history . nil)
           (examples . "N/A")
           (url . "https://help.autodesk.com/cloudhelp/2023/ENU/AutoCAD-AutoLISP-Reference/files/GUID-5F0A5635-0DCB-4A88-BD8E-60EC665342CF.htm")
           (guid . "GUID-5F0A5635-0DCB-4A88-BD8E-60EC665342CF"))))
    *autolisp-reference-parts*))

(setq *autolisp-reference-parts*
  (cons
    '(("trace" .
          ((name . "trace")
           (title . "trace (AutoLISP)")
           (summary . "Aids in AutoLISP debugging")
           (source-kind . "AutoLISP")
           (alphabetic-group . "T")
           (feature-groups . ("Function-Handling"))
           (supported-platforms . "Windows and Mac OS")
           (signature . "(trace [function ...])")
           (arguments . (("function" . "Type: Symbol\nA symbol that names a function. If no argument is supplied, trace has no effect.")))
           (return-values . "Type: Symbol or nil\nThe last function name passed to trace. If no argument is supplied, trace returns nil.")
           (release-information . nil)
           (history . nil)
           (examples . "Define a function named foo and set the trace flag for the function:\n\n(defun foo (x) (if (> x 0) (foo (1- x))))\nFOO\n\n(trace foo)\nFOO\n\nInvoke foo and observe the results:\n\n(foo 3)\nEntering (FOO 3)\nEntering (FOO 2)\nEntering (FOO 1)\nEntering (FOO 0)\nResult: nil\nResult: nil\nResult: nil\nResult: nil\n\nClear the trace flag by invoking untrace:\n\n(untrace foo)\nFOO")
           (url . "https://help.autodesk.com/cloudhelp/2023/ENU/AutoCAD-AutoLISP-Reference/files/GUID-87EEF5AD-2250-401D-B722-0CD122DBAE70.htm")
           (guid . "GUID-87EEF5AD-2250-401D-B722-0CD122DBAE70"))))
    *autolisp-reference-parts*))

(setq *autolisp-reference-entry* nil)

(setq *autolisp-reference-value* "GUID-1A316343-0B68-4DBE-8F49-B4D601CB8FCC")

(setq *autolisp-reference-entry* (cons (cons 'guid *autolisp-reference-value*) *autolisp-reference-entry*))

(setq *autolisp-reference-value* "https://help.autodesk.com/cloudhelp/2023/ENU/AutoCAD-AutoLISP-Reference/files/GUID-1A316343-0B68-4DBE-8F49-B4D601CB8FCC.htm")

(setq *autolisp-reference-entry* (cons (cons 'url *autolisp-reference-value*) *autolisp-reference-entry*))

(setq *autolisp-reference-value* "In the following examples, the UCS is rotated 90 degrees counterclockwise around the WCS Z axis:\n\n(trans '(1.0 2.0 3.0) 0 1)\n(2.0 -1.0 3.0)\n\n(trans '(1.0 2.0 3.0) 1 0)\n(-2.0 1.0 3.0)\n\nFor example, to draw a line from the insertion point of a piece of text (without using Osnap), you convert the text object's insertion point from the text object's OCS to the UCS.\n\n(trans text-insert-point text-ename 1)\n\nYou can then pass the result to the From Point prompt.\n\nConversely, you must convert point (or displacement) values to their destination OCS before feeding them to entmod. For example, if you want to move a circle (without using the AutoCAD MOVE command) by the UCS-relative offset (1,2,3), you need to convert the displacement from the UCS to the circle's OCS:\n\n(trans '(1 2 3) 1 circle-ename)\n\nThen you add the resulting displacement to the circle's center point.\n\nFor exam")

(setq *autolisp-reference-value* (strcat *autolisp-reference-value* "ple, if you have a point entered by the user and want to find out which end of a line it looks closer to, you convert the user's point from the UCS to the DCS.\n\n(trans user-point 1 2)\n\nThen you convert each of the line's endpoints from the OCS to the DCS.\n\n(trans endpoint line-ename 2)\n\nFrom there you can compute the distance between the user's point and each endpoint of the line (ignoring the Z coordinates) to determine which end looks closer."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nA 3D point (or displacement) in the requested to coordinate system.")

(setq *autolisp-reference-entry* (cons (cons 'return-values *autolisp-reference-value*) *autolisp-reference-entry*))

(setq *autolisp-reference-value* nil)

(setq *autolisp-reference-string* "Type:List\nIf present and is not nil, this argument specifies that pt is to be treated as a 3D displacement rather than as a point.")

(setq *autolisp-reference-value* (cons (cons "disp" *autolisp-reference-string*) *autolisp-reference-value*))

(setq *autolisp-reference-string* "Type: Integer, List, or Ename (entity name)\nAn integer code, entity name, or 3D extrusion vector identifying the coordinate system of the returned point. See the from argument for a list of valid integer codes.")

(setq *autolisp-reference-value* (cons (cons "to" *autolisp-reference-string*) *autolisp-reference-value*))

(setq *autolisp-reference-string* "Type: Integer, List, or Ename (entity name)\nAn integer code, entity name, or 3D extrusion vector identifying the coordinate system in which pt is expressed. The integer code can be one of the following:\n0 -- World (WCS)\n1 -- User (current UCS)\n2 -- If used with code 0 or 1, this indicates the Display Coordinate System (DCS) of the current viewport. When used with code 3, it indicates the DCS of the current model space viewport.\n3 -- Paper space DCS (used only with code 2)")

(setq *autolisp-reference-value* (cons (cons "from" *autolisp-reference-string*) *autolisp-reference-value*))

(setq *autolisp-reference-string* "Type: List\nA list of three reals that can be interpreted as either a 3D point or a 3D displacement (vector).")

(setq *autolisp-reference-value* (cons (cons "pt" *autolisp-reference-string*) *autolisp-reference-value*))

(setq *autolisp-reference-entry* (cons (cons 'arguments *autolisp-reference-value*) *autolisp-reference-entry*))

(setq *autolisp-reference-value* "(trans pt from to [disp])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Conversion"))

(setq *autolisp-reference-entry* (cons (cons 'feature-groups *autolisp-reference-value*) *autolisp-reference-entry*))

(setq *autolisp-reference-value* "T")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Translates a point (or a displacement) from one coordinate system to another")

(setq *autolisp-reference-entry* (cons (cons 'summary *autolisp-reference-value*) *autolisp-reference-entry*))

(setq *autolisp-reference-value* "trans (AutoLISP)")

(setq *autolisp-reference-entry* (cons (cons 'title *autolisp-reference-value*) *autolisp-reference-entry*))

(setq *autolisp-reference-value* "trans")

(setq *autolisp-reference-entry* (cons (cons 'name *autolisp-reference-value*) *autolisp-reference-entry*))

(setq *autolisp-reference-parts* (cons (list (cons "trans" *autolisp-reference-entry*)) *autolisp-reference-parts*))

(setq *autolisp-reference-parts*
  (cons
    '(("type" .
          ((name . "type")
           (title . "type (AutoLISP)")
           (summary . "Returns the type of a specified item")
           (source-kind . "AutoLISP")
           (alphabetic-group . "T")
           (feature-groups . ("Symbol-Handling"))
           (supported-platforms . "Windows and Mac OS")
           (signature . "(type item)")
           (arguments . (("item" . "Type: Varies\nA symbol.")))
           (return-values . "Type: Varies or nil\nThe data type of item. Items that evaluate to nil (such as unassigned symbols) return nil. The data type is returned as one of the atoms listed in the following table:")
           (release-information . nil)
           (history . nil)
           (examples . "For example, given the following assignments:\n\n(setq a 123 r 3.45 s \"Hello!\" x '(a b c))\n(setq f (open \"name\" \"r\"))\n\nthen\n\n(type 'a)                   returns  SYM\n(type a)                    returns  INT\n(type f)                    returns  FILE\n(type r)                    returns  REAL\n(type s)                    returns  STR\n(type x)                    returns  LIST\n(type +)                    returns  SUBR\n(type nil)                  returns  nil\n\nThe following code example uses the type function on the argument passed to it:\n\n(defun isint (a)\n   (if (= (type a) 'INT)    is TYPE integer?\n     T                      yes, return T\n     nil                    no, return nil\n   )\n)")
           (url . "https://help.autodesk.com/cloudhelp/2023/ENU/AutoCAD-AutoLISP-Reference/files/GUID-506C9CC8-B0BD-4A4C-B4C2-006750504509.htm")
           (guid . "GUID-506C9CC8-B0BD-4A4C-B4C2-006750504509"))))
    *autolisp-reference-parts*))

(setq *autolisp-reference-parts*
  (cons
    '(("unload_dialog" .
          ((name . "unload_dialog")
           (title . "unload_dialog (AutoLISP/DCL)")
           (summary . "Unloads a DCL file")
           (source-kind . "AutoLISP/DCL")
           (alphabetic-group . "U")
           (feature-groups . ("Dialog Box Opening and Closing Functions Reference (AutoLISP/DCL)"))
           (supported-platforms . "Windows and Mac OS")
           (signature . "(unload_dialog dcl_id)")
           (arguments . (("dcl_id" . "Type: Integer\nA DCL file identifier obtained from a previous load_dialog call.")))
           (return-values . "Type: nil\nAlways returns nil.")
           (release-information . "Releases:\n- AutoCAD R12 and later on Windows\n- AutoCAD 2021 and later on Mac OS")
           (history . nil)
           (examples . "N/A")
           (url . "https://help.autodesk.com/cloudhelp/2023/ENU/AutoCAD-AutoLISP-Reference/files/GUID-101DA923-3246-4518-A45E-22B0E4B84192.htm")
           (guid . "GUID-101DA923-3246-4518-A45E-22B0E4B84192"))))
    *autolisp-reference-parts*))

(setq *autolisp-reference-parts*
  (cons
    '(("untrace" .
          ((name . "untrace")
           (title . "untrace (AutoLISP)")
           (summary . "Clears the trace flag for the specified functions")
           (source-kind . "AutoLISP")
           (alphabetic-group . "U")
           (feature-groups . ("Function-Handling"))
           (supported-platforms . "Windows and Mac OS")
           (signature . "(untrace [function ...])")
           (arguments . (("function" . "Type: Symbol\nA symbol that names a function. If function is not specified, untrace has no effect.")))
           (return-values . "Type: Symbol or nil\nThe last function name passed to untrace. If function was not specified, untrace returns nil.")
           (release-information . nil)
           (history . nil)
           (examples . "The following command clears the trace flag for function foo:\n\n(untrace foo)\nFOO")
           (url . "https://help.autodesk.com/cloudhelp/2023/ENU/AutoCAD-AutoLISP-Reference/files/GUID-44FB0D76-668A-449C-9C17-4BCD259577E9.htm")
           (guid . "GUID-44FB0D76-668A-449C-9C17-4BCD259577E9"))))
    *autolisp-reference-parts*))

(setq *autolisp-reference-parts*
  (cons
    '(("vector_image" .
          ((name . "vector_image")
           (title . "vector_image (AutoLISP/DCL)")
           (summary . "Draws a vector in the currently active dialog box image")
           (source-kind . "AutoLISP/DCL")
           (alphabetic-group . "V")
           (feature-groups . ("Image Tile-Handling Functions Reference (AutoLISP/DCL)"))
           (supported-platforms . "Windows and Mac OS")
           (signature . "(vector_image x1 y1 x2 y2 color)")
           (arguments . (("x1" . "Type: Integer\nX coordinate of the first point.")
                           ("y1" . "Type: Integer\nY coordinate of the first point.")
                           ("x2" . "Type: Integer\nX coordinate of the second point.")
                           ("y2" . "Type: Integer\nY coordinate of the second point.")
                           ("color" . "Type: Integer\nAn AutoCAD color number, or one of the logical color numbers shown in the following table:")))
           (return-values . "Type: Integer\nA numeric value representing the color of the vector.")
           (release-information . "Releases:\n- AutoCAD R12 and later on Windows\n- AutoCAD 2021 and later on Mac OS")
           (history . nil)
           (examples . "(setq color -2) ;; color of AutoCAD drawing area\n(vector_image\n  0\n  0\n  (dimx_tile \"slide_tile\")\n  (dimy_tile \"slide_tile\")\n  color\n)\n(end_image)")
           (url . "https://help.autodesk.com/cloudhelp/2023/ENU/AutoCAD-AutoLISP-Reference/files/GUID-28CC07ED-CBD2-47EF-9866-1AB31DCEA34F.htm")
           (guid . "GUID-28CC07ED-CBD2-47EF-9866-1AB31DCEA34F"))))
    *autolisp-reference-parts*))

(setq *autolisp-reference-parts*
  (cons
    '(("ver" .
          ((name . "ver")
           (title . "ver (AutoLISP)")
           (summary . "Returns a string that contains the current AutoLISP version number")
           (source-kind . "AutoLISP")
           (alphabetic-group . "V")
           (feature-groups . ("Query and Command"))
           (supported-platforms . "Windows and Mac OS")
           (signature . "(ver)")
           (arguments . nil)
           (return-values . "Type: String\nTextual value returned takes the following form:\n\"environment version (nn)\"\nwhere environment is the name of the AutoLISP environment, version is the current version number, and nn is a two-letter language description.\nExamples of the two-letter language descriptions are as follows:\n(de) German\n(en) US/UK\n(es) Spanish\n(fr) French\n(it) Italian")
           (release-information . nil)
           (history . nil)
           (examples . "Windows\n\n(ver)\n\"Visual LISP <release> (en)\"\n\nMac OS\n\n(ver)\n\"MacOS AutoLISP <release> (en)\"")
           (url . "https://help.autodesk.com/cloudhelp/2023/ENU/AutoCAD-AutoLISP-Reference/files/GUID-6E5DF4E1-5386-47A2-AEF3-488AA068FA15.htm")
           (guid . "GUID-6E5DF4E1-5386-47A2-AEF3-488AA068FA15"))))
    *autolisp-reference-parts*))

(setq *autolisp-reference-parts*
  (cons
    '(("vl-acad-defun" .
          ((name . "vl-acad-defun")
           (title . "vl-acad-defun (AutoLISP)")
           (summary . "Defines an AutoLISP function symbol as an external subroutine")
           (source-kind . "AutoLISP")
           (alphabetic-group . "V")
           (feature-groups . nil)
           (supported-platforms . "Windows and Mac OS")
           (signature . "(vl-acad-defun 'symbol)")
           (arguments . (("symbol" . "Type: Subroutine or Symbol\nA symbol identifying a function.")))
           (return-values . "Type: Integer\nA numeric value.")
           (release-information . nil)
           (history . nil)
           (examples . "None")
           (url . "https://help.autodesk.com/cloudhelp/2023/ENU/AutoCAD-AutoLISP-Reference/files/GUID-D15CB87F-5B69-4BC3-B8BB-E45D57602B27.htm")
           (guid . "GUID-D15CB87F-5B69-4BC3-B8BB-E45D57602B27"))))
    *autolisp-reference-parts*))

(setq *autolisp-reference-parts*
  (cons
    '(("vl-acad-undefun" .
          ((name . "vl-acad-undefun")
           (title . "vl-acad-undefun (AutoLISP)")
           (summary . "Undefines an AutoLISP function symbol so it is no longer available to ObjectARX applications")
           (source-kind . "AutoLISP")
           (alphabetic-group . "V")
           (feature-groups . nil)
           (supported-platforms . "Windows and Mac OS")
           (signature . "(vl-acad-undefun 'symbol)")
           (arguments . (("symbol" . "Type: Subroutine or Symbol\nA symbol identifying a function.")))
           (return-values . "Type: Integer or nil\nA numeric value if successful; nil if unsuccessful (for example, the function was not defined in AutoLISP).")
           (release-information . nil)
           (history . nil)
           (examples . "None")
           (url . "https://help.autodesk.com/cloudhelp/2023/ENU/AutoCAD-AutoLISP-Reference/files/GUID-81CEB01F-8A57-4465-A4F9-CE2E357D692B.htm")
           (guid . "GUID-81CEB01F-8A57-4465-A4F9-CE2E357D692B"))))
    *autolisp-reference-parts*))

(setq *autolisp-reference-parts*
  (cons
    '(("vl-arx-import" .
          ((name . "vl-arx-import")
           (title . "vl-arx-import (AutoLISP)")
           (summary . "Imports ObjectARX functions into a separate-namespace VLX")
           (source-kind . "AutoLISP")
           (alphabetic-group . "V")
           (feature-groups . ("VLX Namespace"))
           (supported-platforms . "Windows and Mac OS")
           (signature . "(vl-arx-import ['function | application])")
           (arguments . (("function" . "Type: String\nSymbol name for the function to import.")
                           ("application" . "Type: String\nApplication name whose functions are to be imported.")))
           (return-values . "Type: nil\nBy default, separate-namespace VLX applications do not import any functions from ObjectARX applications. Use vl-arx-import to explicitly import functions from ObjectARX applications.\nIf executed from a document VLX, this function does nothing and returns nil, as all ADS-DEFUN function names are automatically imported to document VLX applications.")
           (release-information . nil)
           (history . nil)
           (examples . "To see how vl-arx-import works, try the following:\n\nIn the example above, you could have replaced the vl-arx-import call with the following:\n\n(vl-arx-import \"geomcal.crx\")\n\nThis would import all functions defined in geomcal.crx, including c:cal.")
           (url . "https://help.autodesk.com/cloudhelp/2023/ENU/AutoCAD-AutoLISP-Reference/files/GUID-1729FD01-3773-45BD-8AFD-2CA3D4F1B111.htm")
           (guid . "GUID-1729FD01-3773-45BD-8AFD-2CA3D4F1B111"))))
    *autolisp-reference-parts*))

(setq *autolisp-reference-parts*
  (cons
    '(("vl-bb-ref" .
          ((name . "vl-bb-ref")
           (title . "vl-bb-ref (AutoLISP)")
           (summary . "Returns the value of a variable from the blackboard namespace")
           (source-kind . "AutoLISP")
           (alphabetic-group . "V")
           (feature-groups . ("Namespace Communication"))
           (supported-platforms . "Windows and Mac OS")
           (signature . "(vl-bb-ref 'variable)")
           (arguments . (("'variable" . "Type: Symbol\nA symbol identifying the variable to be retrieved.")))
           (return-values . "Type: Integer, Real, String, List, Ename (entity name), T, or nil\nThe value of the variable named by symbol.")
           (release-information . nil)
           (history . nil)
           (examples . "Set a variable in the blackboard:\n\n(vl-bb-set 'foobar \"Root toot toot\")\n\"Root toot toot\"\n\nUse vl-bb-ref to retrieve the value of foobar from the blackboard:\n\n(vl-bb-ref 'foobar)\n\"Root toot toot\"")
           (url . "https://help.autodesk.com/cloudhelp/2023/ENU/AutoCAD-AutoLISP-Reference/files/GUID-F4DAAAA4-5A96-4AFF-B8AE-C1F4F91C80C9.htm")
           (guid . "GUID-F4DAAAA4-5A96-4AFF-B8AE-C1F4F91C80C9"))))
    *autolisp-reference-parts*))

(setq *autolisp-reference-parts*
  (cons
    '(("vl-bb-set" .
          ((name . "vl-bb-set")
           (title . "vl-bb-set (AutoLISP)")
           (summary . "Sets a variable in the blackboard namespace")
           (source-kind . "AutoLISP")
           (alphabetic-group . "V")
           (feature-groups . ("Namespace Communication"))
           (supported-platforms . "Windows and Mac OS")
           (signature . "(vl-bb-set 'symbol value)")
           (arguments . (("'symbol" . "Type: Symbol\nA symbol naming the variable to be set.")
                           ("value" . "Type: Integer, Real, String, List, Ename (entity name), T, or nil\nAny value, except a function.")))
           (return-values . "Type: Integer, Real, String, List, Ename (entity name), T, or nil\nThe value you assigned to symbol.")
           (release-information . nil)
           (history . nil)
           (examples . "(vl-bb-set 'foobar \"Root toot toot\")\n\"Root toot toot\"\n\n(vl-bb-ref 'foobar)\n\"Root toot toot\"")
           (url . "https://help.autodesk.com/cloudhelp/2023/ENU/AutoCAD-AutoLISP-Reference/files/GUID-2B1484FC-BBD1-408B-A8A0-DB931363630F.htm")
           (guid . "GUID-2B1484FC-BBD1-408B-A8A0-DB931363630F"))))
    *autolisp-reference-parts*))

(setq *autolisp-reference-entry* nil)

(setq *autolisp-reference-value* "GUID-E08CC2A6-787A-422F-8BD3-18812996794C")

(setq *autolisp-reference-entry* (cons (cons 'guid *autolisp-reference-value*) *autolisp-reference-entry*))

(setq *autolisp-reference-value* "https://help.autodesk.com/cloudhelp/2023/ENU/AutoCAD-AutoLISP-Reference/files/GUID-E08CC2A6-787A-422F-8BD3-18812996794C.htm")

(setq *autolisp-reference-entry* (cons (cons 'url *autolisp-reference-value*) *autolisp-reference-entry*))

(setq *autolisp-reference-value* "If the function invoked by vl-catch-all-apply completes successfully, it is the same as using apply, as the following examples show:\n\n(setq catchit (apply '/ '(50 5)))\n10\n\n(setq catchit (vl-catch-all-apply '/ '(50 5)))\n10\n\nThe benefit of using vl-catch-all-apply is that it allows you to intercept errors and continue processing. See what happens when you try to divide by zero using apply:\n\n(setq catchit (apply '/ '(50 0)))\n; error: divide by zero\n\nWhen you use apply, an exception occurs and an error message displays. Here is the same operation using vl-catch-all-apply:\n\n(setq catchit (vl-catch-all-apply '/ '(50 0)))\n#<%catch-all-apply-error%>\n\nThe vl-catch-all-apply function traps the error and returns an error object. Use vl-catch-all-error-message to see the error message contained in the error object:\n\n(vl-catch-all-error-message catchit)\n\"divide by zero\"")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, List, Ename (entity name), T, nil, or catch-all-apply-error\nThe result of the function call, if successful. If an error occurs, vl-catch-all-apply returns an error object.")

(setq *autolisp-reference-entry* (cons (cons 'return-values *autolisp-reference-value*) *autolisp-reference-entry*))

(setq *autolisp-reference-value* nil)

(setq *autolisp-reference-string* "Type: List\nA list containing arguments to be passed to the function.")

(setq *autolisp-reference-value* (cons (cons "list" *autolisp-reference-string*) *autolisp-reference-value*))

(setq *autolisp-reference-string* "Type: Symbol\nA function. The function argument can be either a symbol identifying a defun or lambda expression.")

(setq *autolisp-reference-value* (cons (cons "'function" *autolisp-reference-string*) *autolisp-reference-value*))

(setq *autolisp-reference-entry* (cons (cons 'arguments *autolisp-reference-value*) *autolisp-reference-entry*))

(setq *autolisp-reference-value* "(vl-catch-all-apply 'function list)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Error-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Passes a list of arguments to a specified function and traps any exceptions")

(setq *autolisp-reference-entry* (cons (cons 'summary *autolisp-reference-value*) *autolisp-reference-entry*))

(setq *autolisp-reference-value* "vl-catch-all-apply (AutoLISP)")

(setq *autolisp-reference-entry* (cons (cons 'title *autolisp-reference-value*) *autolisp-reference-entry*))

(setq *autolisp-reference-value* "vl-catch-all-apply")

(setq *autolisp-reference-entry* (cons (cons 'name *autolisp-reference-value*) *autolisp-reference-entry*))

(setq *autolisp-reference-parts* (cons (list (cons "vl-catch-all-apply" *autolisp-reference-entry*)) *autolisp-reference-parts*))

(setq *autolisp-reference-parts*
  (cons
    '(("vl-catch-all-error-message" .
          ((name . "vl-catch-all-error-message")
           (title . "vl-catch-all-error-message (AutoLISP)")
           (summary . "Returns a string from an error object")
           (source-kind . "AutoLISP")
           (alphabetic-group . "V")
           (feature-groups . ("Error-Handling"))
           (supported-platforms . "Windows and Mac OS")
           (signature . "(vl-catch-all-error-message error-obj)")
           (arguments . (("error-obj" . "Type: catch-all-apply-error\nAn error object returned by vl-catch-all-apply.")))
           (return-values . "Type: String\nA textual value containing an error message.")
           (release-information . nil)
           (history . nil)
           (examples . "Divide by zero using vl-catch-all-apply:\n\n(setq catchit (vl-catch-all-apply '/ '(50 0)))\n#<%catch-all-apply-error%>\n\nThe vl-catch-all-apply function traps the error and returns an error object. Use vl-catch-all-error-message to see the error message contained in the error object:\n\n(vl-catch-all-error-message catchit)\n\"divide by zero\"")
           (url . "https://help.autodesk.com/cloudhelp/2023/ENU/AutoCAD-AutoLISP-Reference/files/GUID-C703867D-7B64-480D-BE34-45A63BA02AB7.htm")
           (guid . "GUID-C703867D-7B64-480D-BE34-45A63BA02AB7"))))
    *autolisp-reference-parts*))

(setq *autolisp-reference-parts*
  (cons
    '(("vl-catch-all-error-p" .
          ((name . "vl-catch-all-error-p")
           (title . "vl-catch-all-error-p (AutoLISP)")
           (summary . "Determines whether an argument is an error object returned from vl-catch-all-apply")
           (source-kind . "AutoLISP")
           (alphabetic-group . "V")
           (feature-groups . ("Error-Handling"))
           (supported-platforms . "Windows and Mac OS")
           (signature . "(vl-catch-all-error-p arg)")
           (arguments . (("arg" . "Type: Integer, Real, String, List, Subroutine, Ename (entity name), T, nil, or catch-all-apply-error\nAny argument.")))
           (return-values . "Type: T or nil\nT, if the supplied argument is an error object returned from vl-catch-all-apply; otherwise nil.")
           (release-information . nil)
           (history . nil)
           (examples . "Divide by zero using vl-catch-all-apply:\n\n(setq catchit (vl-catch-all-apply '/ '(50 0)))\n#<%catch-all-apply-error%>\n\nUse vl-catch-all-error-p to determine if the value returned by vl-catch-all-apply is an error object:\n\n(vl-catch-all-error-p catchit)\nT")
           (url . "https://help.autodesk.com/cloudhelp/2023/ENU/AutoCAD-AutoLISP-Reference/files/GUID-14CADE53-54C6-437D-8F3C-14845E08591C.htm")
           (guid . "GUID-14CADE53-54C6-437D-8F3C-14845E08591C"))))
    *autolisp-reference-parts*))

(setq *autolisp-reference-entry* nil)

(setq *autolisp-reference-value* "GUID-6F1AAB6B-D5B1-426A-A463-0CBE93E4D956")

(setq *autolisp-reference-entry* (cons (cons 'guid *autolisp-reference-value*) *autolisp-reference-entry*))

(setq *autolisp-reference-value* "https://help.autodesk.com/cloudhelp/2023/ENU/AutoCAD-AutoLISP-Reference/files/GUID-6F1AAB6B-D5B1-426A-A463-0CBE93E4D956.htm")

(setq *autolisp-reference-entry* (cons (cons 'url *autolisp-reference-value*) *autolisp-reference-entry*))

(setq *autolisp-reference-value* "The differences between command and vl-cmdf are easier to see if you enter the following calls at the AutoCAD Command prompt:\n\nCommand: (command \"._line\" (getpoint \"point?\") '(0 0) \"\")\n\nline Specify first point: point?\n\nSpecify next point or [Undo]:\n\nCommand: nil\n\nUsing command, the LINE command executes first; then the getpoint function is called.\n\nCommand: (vl-cmdf \"._line\" (getpoint \"point?\") '(0 0) \"\")\n\npoint?line Specify first point:\n\nSpecify next point or [Undo]:\n\nCommand: T\n\nUsing vl-cmdf, the getpoint function is called first (notice the “point?” prompt from getpoint); then the LINE command executes.\n\nThe following examples show the same commands, but pass an invalid point list argument to the LINE command. Notice how the results differ:\n\nCommand: (command \"._line\" (getpoint \"point?\") '(0) \"\")\n\nline Specify first point: point?\n\nSpecif")

(setq *autolisp-reference-value* (strcat *autolisp-reference-value* "y next point or [Undo]:\n\nCommand: ERASE nil\n\nSelect objects: Specify opposite corner: *Cancel*\n\n0 found\n\nThe command function passes each argument in turn to AutoCAD, without evaluating the argument, so the invalid point list is undetected.\n\nCommand: (vl-cmdf \"._line\" (getpoint \"point?\") '(0) \"\")\n\npoint?Application ERROR: Invalid entity/point list.\n\nnil\n\nBecause vl-cmdf evaluates each argument before passing the command to AutoCAD, the invalid point list is detected and the command is not executed."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T\nAlways returns T.")

(setq *autolisp-reference-entry* (cons (cons 'return-values *autolisp-reference-value*) *autolisp-reference-entry*))

(setq *autolisp-reference-value* nil)

(setq *autolisp-reference-string* "Type: Integer, Real, String, List, or Ename (entity name)\nAutoCAD commands and their options.\nThe arguments to the vl-cmdf function can be strings, reals, integers, or points, as expected by the prompt sequence of the executed command. A null string (\"\") is equivalent to pressing Enter on the keyboard. Invoking vl-cmdf with no argument is equivalent to pressing Esc and cancels most AutoCAD commands.")

(setq *autolisp-reference-value* (cons (cons "arguments" *autolisp-reference-string*) *autolisp-reference-value*))

(setq *autolisp-reference-entry* (cons (cons 'arguments *autolisp-reference-value*) *autolisp-reference-entry*))

(setq *autolisp-reference-value* "(vl-cmdf [arguments ...])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Query and Command"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Executes an AutoCAD command")

(setq *autolisp-reference-entry* (cons (cons 'summary *autolisp-reference-value*) *autolisp-reference-entry*))

(setq *autolisp-reference-value* "vl-cmdf (AutoLISP)")

(setq *autolisp-reference-entry* (cons (cons 'title *autolisp-reference-value*) *autolisp-reference-entry*))

(setq *autolisp-reference-value* "vl-cmdf")

(setq *autolisp-reference-entry* (cons (cons 'name *autolisp-reference-value*) *autolisp-reference-entry*))

(setq *autolisp-reference-parts* (cons (list (cons "vl-cmdf" *autolisp-reference-entry*)) *autolisp-reference-parts*))

(setq *autolisp-reference-parts*
  (cons
    '(("vl-consp" .
          ((name . "vl-consp")
           (title . "vl-consp (AutoLISP)")
           (summary . "Determines whether or not a list is nil")
           (source-kind . "AutoLISP")
           (alphabetic-group . "V")
           (feature-groups . ("List Manipulation"))
           (supported-platforms . "Windows and Mac OS")
           (signature . "(vl-consp list-variable)")
           (arguments . (("list-variable" . "Type: Integer, Real, String, List, Subroutine, Ename (entity name), T, nil, or catch-all-apply-error\nA list.")))
           (return-values . "Type: T or nil\nT, if list-variable is a list and is not nil; otherwise nil.")
           (release-information . nil)
           (history . nil)
           (examples . "(vl-consp nil)\nnil\n\n(vl-consp t)\nnil\n\n(vl-consp (cons 0 \"LINE\"))\nT")
           (url . "https://help.autodesk.com/cloudhelp/2023/ENU/AutoCAD-AutoLISP-Reference/files/GUID-36CFF983-0020-4300-845B-BA9768F1B4E8.htm")
           (guid . "GUID-36CFF983-0020-4300-845B-BA9768F1B4E8"))))
    *autolisp-reference-parts*))

(setq *autolisp-reference-entry* nil)

(setq *autolisp-reference-value* "GUID-C28C0CB0-FBBE-4AA8-BAC4-2FF222772514")

(setq *autolisp-reference-entry* (cons (cons 'guid *autolisp-reference-value*) *autolisp-reference-entry*))

(setq *autolisp-reference-value* "https://help.autodesk.com/cloudhelp/2023/ENU/AutoCAD-AutoLISP-Reference/files/GUID-C28C0CB0-FBBE-4AA8-BAC4-2FF222772514.htm")

(setq *autolisp-reference-entry* (cons (cons 'url *autolisp-reference-value*) *autolisp-reference-entry*))

(setq *autolisp-reference-value* "Windows\n\n(vl-directory-files \"c:/acadwin\" \"acad*.exe\")\n(\"ACAD.EXE\" \"ACADAPP.EXE\" \"ACADL.EXE\" \"ACADPS.EXE\")\n\n(vl-directory-files \"e:/acadwin\" nil -1)\n(\".\" \"..\" \"SUPPORT\" \"SAMPLE\" \"ADS\" \"FONTS\" \"IGESFONT\" \"SOURCE\" \"ASE\")\n\n(vl-directory-files \"E:/acad\" nil -1)\n(\".\" \"..\" \"WIN\" \"COM\" \"DOS\")\n\nMac OS\n\n(vl-directory-files \"/myutilities/lsp\" \"*.lsp\")\n(\".DS_Store\" \"utilities.lsp\" \"blk-insert.lsp\")\n\n(vl-directory-files \"/myutilities\" nil -1)\n(\".\" \"..\" \"Help\" \"Lsp\" \"Support\")")

(setq *autolisp-reference-entry* (cons (cons 'examples *autolisp-reference-value*) *autolisp-reference-entry*))

(setq *autolisp-reference-value* "AutoCAD 2021\n- directory\n- and\n- pattern\n- arguments previously accepted ASCII text strings, but they now accept Unicode text strings.\n- Return value was modified to support Unicode characters and might be different than earlier releases. For example,\n- (vl-directory-files \"c:/\")\n- previously returned the directory name \"abc中\" as \"abc?\", but now correctly returns the directory name as \"abc中\". Also previously passing a directory name with a Unicode character returned a value of\n- nil\n- even if the directory existed.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: List or nil\nA list of file and path names; otherwise nil if no files match the specified pattern.")

(setq *autolisp-reference-entry* (cons (cons 'return-values *autolisp-reference-value*) *autolisp-reference-entry*))

(setq *autolisp-reference-value* nil)

(setq *autolisp-reference-string* "Type: Integer\nValue that indicates whether the returned list should include directory names. Specify one of the following:\n-1 -- List directories only\n0 -- List files and directories (the default)\n1 -- List files only")

(setq *autolisp-reference-value* (cons (cons "directories" *autolisp-reference-string*) *autolisp-reference-value*))

(setq *autolisp-reference-string* "Type: String\nValid wildcard pattern for the file name; if nil or absent, vl-directory-files assumes \"*.*\".")

(setq *autolisp-reference-value* (cons (cons "pattern" *autolisp-reference-string*) *autolisp-reference-value*))

(setq *autolisp-reference-string* "Type: String\nDirectory name to collect files for; if nil or absent, vl-directory-files uses the current directory.")

(setq *autolisp-reference-value* (cons (cons "directory" *autolisp-reference-string*) *autolisp-reference-value*))

(setq *autolisp-reference-entry* (cons (cons 'arguments *autolisp-reference-value*) *autolisp-reference-entry*))

(setq *autolisp-reference-value* "(vl-directory-files [directory pattern directories])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Lists all files in a given directory")

(setq *autolisp-reference-entry* (cons (cons 'summary *autolisp-reference-value*) *autolisp-reference-entry*))

(setq *autolisp-reference-value* "vl-directory-files (AutoLISP)")

(setq *autolisp-reference-entry* (cons (cons 'title *autolisp-reference-value*) *autolisp-reference-entry*))

(setq *autolisp-reference-value* "vl-directory-files")

(setq *autolisp-reference-entry* (cons (cons 'name *autolisp-reference-value*) *autolisp-reference-entry*))

(setq *autolisp-reference-parts* (cons (list (cons "vl-directory-files" *autolisp-reference-entry*)) *autolisp-reference-parts*))

(setq *autolisp-reference-parts*
  (cons
    '(("vl-doc-export" .
          ((name . "vl-doc-export")
           (title . "vl-doc-export (AutoLISP)")
           (summary . "Makes a function available to the current document")
           (source-kind . "AutoLISP")
           (alphabetic-group . "V")
           (feature-groups . ("VLX Namespace"))
           (supported-platforms . "Windows only")
           (signature . "(vl-doc-export 'function)")
           (arguments . (("'function" . "Type: Subroutine\nA symbol naming the function to be exported.")))
           (return-values . "Type: T\nAlways returns T.")
           (release-information . nil)
           (history . nil)
           (examples . "The following code shows the contents of a file named kertrats.lsp. This file is compiled into a VLX that runs in its own namespace. The VLX file is named kertrats.vlx. The vl-doc-export call makes the kertrats function visible to any document that loads kertrats.vlx:\n\n(vl-doc-export 'kertrats)\n(defun kertrats ()\n  (princ \"This function goes nowhere\")\n)")
           (url . "https://help.autodesk.com/cloudhelp/2023/ENU/AutoCAD-AutoLISP-Reference/files/GUID-696970BC-3669-412C-8194-7ADD950EE7BA.htm")
           (guid . "GUID-696970BC-3669-412C-8194-7ADD950EE7BA"))))
    *autolisp-reference-parts*))

(setq *autolisp-reference-parts*
  (cons
    '(("vl-doc-import" .
          ((name . "vl-doc-import")
           (title . "vl-doc-import (AutoLISP)")
           (summary . "Imports a previously exported function into a VLX namespace")
           (source-kind . "AutoLISP")
           (alphabetic-group . "V")
           (feature-groups . ("VLX Namespace"))
           (supported-platforms . "Windows only")
           (signature . "(vl-doc-import application ['function ...])")
           (arguments . (("application" . "Type: String\nName of the VLX application whose functions are to be imported. Do not include the .vlx extension in the name.")
                           ("function" . "Type: Subroutine\nOne or more symbols naming functions to be imported. If no functions are specified, all functions exported by application will be imported.")))
           (return-values . "Type: nil or error\nnil if successful; otherwise an error occurs")
           (release-information . nil)
           (history . nil)
           (examples . "Import function ldataget from the ldatatest application:\n\n(vl-doc-import \"ldatatest\" 'ldataget)\nnil")
           (url . "https://help.autodesk.com/cloudhelp/2023/ENU/AutoCAD-AutoLISP-Reference/files/GUID-68A6C7D0-8EE9-4F78-829A-86D08D2BD193.htm")
           (guid . "GUID-68A6C7D0-8EE9-4F78-829A-86D08D2BD193"))))
    *autolisp-reference-parts*))

(setq *autolisp-reference-parts*
  (cons
    '(("vl-doc-ref" .
          ((name . "vl-doc-ref")
           (title . "vl-doc-ref (AutoLISP)")
           (summary . "Retrieves the value of a variable from the current document's namespace")
           (source-kind . "AutoLISP")
           (alphabetic-group . "V")
           (feature-groups . ("VLX Namespace"))
           (supported-platforms . "Windows and Mac OS")
           (signature . "(vl-doc-ref 'symbol)")
           (arguments . (("'symbol" . "Type: Symbol\nA symbol naming a variable.")))
           (return-values . "Type: Integer, Real, String, List, Ename (entity name), T, or nil\nThe value of the variable identified by symbol.")
           (release-information . nil)
           (history . nil)
           (examples . "(vl-doc-ref 'foobar)\n\"Rinky dinky stinky\"")
           (url . "https://help.autodesk.com/cloudhelp/2023/ENU/AutoCAD-AutoLISP-Reference/files/GUID-36D04AAD-5555-4A4A-939D-352144FBB1A7.htm")
           (guid . "GUID-36D04AAD-5555-4A4A-939D-352144FBB1A7"))))
    *autolisp-reference-parts*))

(setq *autolisp-reference-parts*
  (cons
    '(("vl-doc-set" .
          ((name . "vl-doc-set")
           (title . "vl-doc-set (AutoLISP)")
           (summary . "Sets the value of a variable in the current document's namespace")
           (source-kind . "AutoLISP")
           (alphabetic-group . "V")
           (feature-groups . ("VLX Namespace"))
           (supported-platforms . "Windows and Mac OS")
           (signature . "(vl-doc-set 'symbol value)")
           (arguments . (("'symbol" . "Type: Symbol\nA symbol naming a variable.")
                           ("value" . "Type: Integer, Real, String, List, Ename (entity name), T, or nil\nAny value.")))
           (return-values . "Type: Integer, Real, String, List, Ename (entity name), T, or nil\nThe value set.")
           (release-information . nil)
           (history . nil)
           (examples . "(vl-doc-set 'foobar \"Rinky dinky stinky\")\n\"Rinky dinky stinky\"")
           (url . "https://help.autodesk.com/cloudhelp/2023/ENU/AutoCAD-AutoLISP-Reference/files/GUID-F6E10804-16C2-4960-AE45-20C296D991E4.htm")
           (guid . "GUID-F6E10804-16C2-4960-AE45-20C296D991E4"))))
    *autolisp-reference-parts*))

(setq *autolisp-reference-entry* nil)

(setq *autolisp-reference-value* "GUID-8BF61C9E-1382-4168-A778-FEA394A361CC")

(setq *autolisp-reference-entry* (cons (cons 'guid *autolisp-reference-value*) *autolisp-reference-entry*))

(setq *autolisp-reference-value* "https://help.autodesk.com/cloudhelp/2023/ENU/AutoCAD-AutoLISP-Reference/files/GUID-8BF61C9E-1382-4168-A778-FEA394A361CC.htm")

(setq *autolisp-reference-entry* (cons (cons 'url *autolisp-reference-value*) *autolisp-reference-entry*))

(setq *autolisp-reference-value* "Check whether there are any empty files in the current directory:\n\n(vl-every\n'(lambda (fnm) (> (vl-file-size fnm) 0))\n   (vl-directory-files nil nil 1))\nT\n\nCheck whether the list of numbers in nlst is ordered by '<=:\n\n(setq nlst (list 0 2 pi pi 4))\n(0 2 3.14159 3.14159 4)\n\n(vl-every '<= nlst (cdr nlst))\nT\n\nCompare the results of the following expressions:\n\n(vl-every '= '(1 2) '(1 3))\nnil\n\n(vl-every '= '(1 2) '(1 2 3))\nT\n\nThe first expression returned nil because vl-every compared the second element in each list and they were not numerically equal. The second expression returned T because vl-every stopped comparing elements after it had processed all the elements in the shorter list (1 2), at which point the lists were numerically equal. If the end of a list is reached, vl-every returns a non-nil value.\n\nThe following example demonstrates the result when vl-every ")

(setq *autolisp-reference-value* (strcat *autolisp-reference-value* "evaluates one list that contains integer elements and another list that is nil:\n\n(setq alist (list 1 2 3 4))\n(1 2 3 4)\n\n(setq junk nil)\nnil\n\n(vl-every '= junk alist)\nT\n\nThe return value is T because vl-every responds to the nil list as if it has reached the end of the list (even though the predicate has not yet been applied to any elements). And since the end of a list has been reached, vl-every returns a non-nil value."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nT, if predicate-function returns a non-nil value for every element combination; otherwise nil.")

(setq *autolisp-reference-entry* (cons (cons 'return-values *autolisp-reference-value*) *autolisp-reference-entry*))

(setq *autolisp-reference-value* nil)

(setq *autolisp-reference-string* "Type: List\nA list to be tested.")

(setq *autolisp-reference-value* (cons (cons "list" *autolisp-reference-string*) *autolisp-reference-value*))

(setq *autolisp-reference-string* "Type: Subroutine or Symbol\nThe test function. This can be any function that accepts as many arguments as there are lists provided with vl-every, and returns T on any user-specified condition. The predicate-function value can take one of the following forms:\n- A symbol (function name)\n- '(LAMBDA (A1 A2) ...)\n- (FUNCTION (LAMBDA (A1 A2) ...))")

(setq *autolisp-reference-value* (cons (cons "predicate-function" *autolisp-reference-string*) *autolisp-reference-value*))

(setq *autolisp-reference-entry* (cons (cons 'arguments *autolisp-reference-value*) *autolisp-reference-entry*))

(setq *autolisp-reference-value* "(vl-every predicate-function list [list ...])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("List Manipulation"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Checks whether the predicate is true for every element combination")

(setq *autolisp-reference-entry* (cons (cons 'summary *autolisp-reference-value*) *autolisp-reference-entry*))

(setq *autolisp-reference-value* "vl-every (AutoLISP)")

(setq *autolisp-reference-entry* (cons (cons 'title *autolisp-reference-value*) *autolisp-reference-entry*))

(setq *autolisp-reference-value* "vl-every")

(setq *autolisp-reference-entry* (cons (cons 'name *autolisp-reference-value*) *autolisp-reference-entry*))

(setq *autolisp-reference-parts* (cons (list (cons "vl-every" *autolisp-reference-entry*)) *autolisp-reference-parts*))

(setq *autolisp-reference-parts*
  (cons
    '(("vl-exit-with-error" .
          ((name . "vl-exit-with-error")
           (title . "vl-exit-with-error (AutoLISP)")
           (summary . "Passes control from an error handler to the *error* function of the calling namespace")
           (source-kind . "AutoLISP")
           (alphabetic-group . "V")
           (feature-groups . ("VLX Namespace"))
           (supported-platforms . "Windows and Mac OS")
           (signature . "(vl-exit-with-error msg)")
           (arguments . (("msg" . "Type: String\nMessage displayed to the user.")))
           (return-values . "Type: None\nNone")
           (release-information . nil)
           (history . nil)
           (examples . "The following code illustrates the use of vl-exit-with-error to pass a string to the *error* function of the calling namespace:\n\n(defun *error* (msg)\n  ... ; processing in VLX namespace/execution context\n(vl-exit-with-error (strcat \"My application bombed! \" msg)))")
           (url . "https://help.autodesk.com/cloudhelp/2023/ENU/AutoCAD-AutoLISP-Reference/files/GUID-718FA582-B7BE-4BA6-8EBF-70B250DF76D8.htm")
           (guid . "GUID-718FA582-B7BE-4BA6-8EBF-70B250DF76D8"))))
    *autolisp-reference-parts*))

(setq *autolisp-reference-parts*
  (cons
    '(("vl-exit-with-value" .
          ((name . "vl-exit-with-value")
           (title . "vl-exit-with-value (AutoLISP)")
           (summary . "Returns a value to the function that invoked the *error* handler from another namespace")
           (source-kind . "AutoLISP")
           (alphabetic-group . "V")
           (feature-groups . ("VLX Namespace"))
           (supported-platforms . "Windows and Mac OS")
           (signature . "(vl-exit-with-value value)")
           (arguments . (("value" . "Type: Integer, Real, String, List, File, Ename (entity name), T, or nil\nAny value.")))
           (return-values . "Type: Integer, Real, String, List, File, Ename (entity name), T, or nil\nvalue provided to the function.")
           (release-information . nil)
           (history . nil)
           (examples . "The following example uses vl-exit-with-value to return the integer value 3 to the function that invoked the VLX:\n\n(defun *error* (msg)\n  ... ; processing in VLX-T namespace/execution context\n  (vl-exit-with-value  3))")
           (url . "https://help.autodesk.com/cloudhelp/2023/ENU/AutoCAD-AutoLISP-Reference/files/GUID-80622A39-A5E8-4E68-824E-E66BD8D3E9DE.htm")
           (guid . "GUID-80622A39-A5E8-4E68-824E-E66BD8D3E9DE"))))
    *autolisp-reference-parts*))

(setq *autolisp-reference-entry* nil)

(setq *autolisp-reference-value* "GUID-12910252-217C-427D-8874-1323611FA74C")

(setq *autolisp-reference-entry* (cons (cons 'guid *autolisp-reference-value*) *autolisp-reference-entry*))

(setq *autolisp-reference-value* "https://help.autodesk.com/cloudhelp/2023/ENU/AutoCAD-AutoLISP-Reference/files/GUID-12910252-217C-427D-8874-1323611FA74C.htm")

(setq *autolisp-reference-entry* (cons (cons 'url *autolisp-reference-value*) *autolisp-reference-entry*))

(setq *autolisp-reference-value* "Windows\n\nCopy autoexec.bat to newauto.bat:\n(vl-file-copy \"c:/autoexec.bat\" \"c:/newauto.bat\")\n1417\nCopy test.bat to newauto.bat:\n(vl-file-copy \"c:/test.bat\" \"c:/newauto.bat\")\nnil\nThe copy fails because newauto.bat already exists, and the append argument was not specified.\nRepeat the previous command, but specify append:\n(vl-file-copy \"c:/test.bat\" \"c:/newauto.bat\" T)\n185\nThe copy is successful because T was specified for the append argument.\n\nMac OS\n\nCopy oldstart.sh to newstart.sh:\n(vl-file-copy \"/oldstart.sh\" \"/newstart.sh\")\n1417\nCopy start.sh to newstart.sh:\n(vl-file-copy \"/start.sh\" \"/newstart.sh\")\nnil\nThe copy fails because newstart.sh already exists, and the append argument was not specified.\nRepeat the previous command, but specify append:\n(vl-file-copy \"/start.sh\" \"/newstart.sh\" T)\n185\nThe copy is successful because T was specified")

(setq *autolisp-reference-value* (strcat *autolisp-reference-value* " for the append argument."))

(setq *autolisp-reference-entry* (cons (cons 'examples *autolisp-reference-value*) *autolisp-reference-entry*))

(setq *autolisp-reference-value* "AutoCAD 2021\n- source-file\n- and\n- destination-file\n- arguments previously accepted ASCII text strings, but they now accept Unicode text strings.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: Integer or nil\nA numeric value, if the copy was successful; otherwise nil.\nSome typical reasons for returning nil are\n- source-file\n- is not readable\n- source-file\n- is a directory\n- append?\n- is absent or\n- nil\n- and\n- destination-file\n- exists\n- destination-file\n- cannot be opened for output (that is, it is an illegal file name or a write-protected file)\n- source-file\n- is the same as\n- destination-file")

(setq *autolisp-reference-entry* (cons (cons 'return-values *autolisp-reference-value*) *autolisp-reference-entry*))

(setq *autolisp-reference-value* nil)

(setq *autolisp-reference-string* "Type: T or nil\nIf specified and not nil, source-file is appended to destination-file (that is, copied to the end of the destination file).")

(setq *autolisp-reference-value* (cons (cons "append" *autolisp-reference-string*) *autolisp-reference-value*))

(setq *autolisp-reference-string* "Type: String\nName of the destination file. If you do not specify a path name, vl-file-copy writes to the AutoCAD default drawing directory.")

(setq *autolisp-reference-value* (cons (cons "destination-file" *autolisp-reference-string*) *autolisp-reference-value*))

(setq *autolisp-reference-string* "Type: String\nName of file to be copied. If you do not specify a full path name, vl-file-copy looks in the AutoCAD default drawing directory.")

(setq *autolisp-reference-value* (cons (cons "source-file" *autolisp-reference-string*) *autolisp-reference-value*))

(setq *autolisp-reference-entry* (cons (cons 'arguments *autolisp-reference-value*) *autolisp-reference-entry*))

(setq *autolisp-reference-value* "(vl-file-copy source-file destination-file [append])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Copies or appends the contents of one file to another file")

(setq *autolisp-reference-entry* (cons (cons 'summary *autolisp-reference-value*) *autolisp-reference-entry*))

(setq *autolisp-reference-value* "vl-file-copy (AutoLISP)")

(setq *autolisp-reference-entry* (cons (cons 'title *autolisp-reference-value*) *autolisp-reference-entry*))

(setq *autolisp-reference-value* "vl-file-copy")

(setq *autolisp-reference-entry* (cons (cons 'name *autolisp-reference-value*) *autolisp-reference-entry*))

(setq *autolisp-reference-parts* (cons (list (cons "vl-file-copy" *autolisp-reference-entry*)) *autolisp-reference-parts*))

(setq *autolisp-reference-entry* nil)

(setq *autolisp-reference-value* "GUID-4CEDC718-EEBB-48A8-A9D3-387F216C12B8")

(setq *autolisp-reference-entry* (cons (cons 'guid *autolisp-reference-value*) *autolisp-reference-entry*))

(setq *autolisp-reference-value* "https://help.autodesk.com/cloudhelp/2023/ENU/AutoCAD-AutoLISP-Reference/files/GUID-4CEDC718-EEBB-48A8-A9D3-387F216C12B8.htm")

(setq *autolisp-reference-entry* (cons (cons 'url *autolisp-reference-value*) *autolisp-reference-entry*))

(setq *autolisp-reference-value* "Windows\n\nDelete newauto.bat:\n(vl-file-delete \"newauto.bat\")\nnil\nNothing was deleted because there is no newauto.bat file in the AutoCAD default drawing directory.\nDelete the newauto.bat file in the c:\\ directory:\n(vl-file-delete \"c:/newauto.bat\")\nT\nThe delete was successful because the full path name identified an existing file.\n\nMac OS\n\nDelete newstart.sh:\n(vl-file-delete \"newstart.sh\")\nnil\nNothing was deleted because there is no newstart.sh file in the AutoCAD default drawing directory.\nDelete the newstart.sh file in the / <root> directory:\n(vl-file-delete \"/newstart.sh\")\nT\nThe delete was successful because the full path name identified an existing file.")

(setq *autolisp-reference-entry* (cons (cons 'examples *autolisp-reference-value*) *autolisp-reference-entry*))

(setq *autolisp-reference-value* "AutoCAD 2021\n- filename\n- argument previously accepted an ASCII text string, but now accepts a Unicode text string.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: T or nil\nT if successful; nil if delete failed.")

(setq *autolisp-reference-entry* (cons (cons 'return-values *autolisp-reference-value*) *autolisp-reference-entry*))

(setq *autolisp-reference-value* nil)

(setq *autolisp-reference-string* "Type: String\nName of the file to be deleted. If you do not specify a full path name, vl-file-delete searches the AutoCAD default drawing directory.")

(setq *autolisp-reference-value* (cons (cons "filename" *autolisp-reference-string*) *autolisp-reference-value*))

(setq *autolisp-reference-entry* (cons (cons 'arguments *autolisp-reference-value*) *autolisp-reference-entry*))

(setq *autolisp-reference-value* "(vl-file-delete filename)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Deletes a file")

(setq *autolisp-reference-entry* (cons (cons 'summary *autolisp-reference-value*) *autolisp-reference-entry*))

(setq *autolisp-reference-value* "vl-file-delete (AutoLISP)")

(setq *autolisp-reference-entry* (cons (cons 'title *autolisp-reference-value*) *autolisp-reference-entry*))

(setq *autolisp-reference-value* "vl-file-delete")

(setq *autolisp-reference-entry* (cons (cons 'name *autolisp-reference-value*) *autolisp-reference-entry*))

(setq *autolisp-reference-parts* (cons (list (cons "vl-file-delete" *autolisp-reference-entry*)) *autolisp-reference-parts*))

(setq *autolisp-reference-entry* nil)

(setq *autolisp-reference-value* "GUID-7EEA5563-33A7-453C-9E96-860F7565808B")

(setq *autolisp-reference-entry* (cons (cons 'guid *autolisp-reference-value*) *autolisp-reference-entry*))

(setq *autolisp-reference-value* "https://help.autodesk.com/cloudhelp/2023/ENU/AutoCAD-AutoLISP-Reference/files/GUID-7EEA5563-33A7-453C-9E96-860F7565808B.htm")

(setq *autolisp-reference-entry* (cons (cons 'url *autolisp-reference-value*) *autolisp-reference-entry*))

(setq *autolisp-reference-value* "Windows\n\n(vl-file-directory-p \"sample\")\nT\n\n(vl-file-directory-p \"yinyang\")\nnil\n\n(vl-file-directory-p \"c:/My Documents\")\nT\n\n(vl-file-directory-p \"c:/My Documents/lisp/yinyang.lsp\")\nnil\n\nMac OS\n\n(vl-file-directory-p \"support\")\nT\n\n(vl-file-directory-p \"xyz\")\nnil\n\n(vl-file-directory-p \"/documents\")\nT\n\n(vl-file-directory-p \"/documents/output.txt\")\nnil")

(setq *autolisp-reference-entry* (cons (cons 'examples *autolisp-reference-value*) *autolisp-reference-entry*))

(setq *autolisp-reference-value* "AutoCAD 2021\n- filename\n- argument previously accepted an ASCII text string, but now accepts a Unicode text string.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: T or nil\nT, if filename is the name of a directory; nil if it is not.")

(setq *autolisp-reference-entry* (cons (cons 'return-values *autolisp-reference-value*) *autolisp-reference-entry*))

(setq *autolisp-reference-value* nil)

(setq *autolisp-reference-string* "Type: String\nFile name. If you do not specify a full path name, vl-file-directory-p searches only the AutoCAD default drawing directory.")

(setq *autolisp-reference-value* (cons (cons "filename" *autolisp-reference-string*) *autolisp-reference-value*))

(setq *autolisp-reference-entry* (cons (cons 'arguments *autolisp-reference-value*) *autolisp-reference-entry*))

(setq *autolisp-reference-value* "(vl-file-directory-p filename)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Determines if a file name refers to a directory")

(setq *autolisp-reference-entry* (cons (cons 'summary *autolisp-reference-value*) *autolisp-reference-entry*))

(setq *autolisp-reference-value* "vl-file-directory-p (AutoLISP)")

(setq *autolisp-reference-entry* (cons (cons 'title *autolisp-reference-value*) *autolisp-reference-entry*))

(setq *autolisp-reference-value* "vl-file-directory-p")

(setq *autolisp-reference-entry* (cons (cons 'name *autolisp-reference-value*) *autolisp-reference-entry*))

(setq *autolisp-reference-parts* (cons (list (cons "vl-file-directory-p" *autolisp-reference-entry*)) *autolisp-reference-parts*))

(setq *autolisp-reference-entry* nil)

(setq *autolisp-reference-value* "GUID-188B957C-4CDF-41C7-99BE-8080FA587F74")

(setq *autolisp-reference-entry* (cons (cons 'guid *autolisp-reference-value*) *autolisp-reference-entry*))

(setq *autolisp-reference-value* "https://help.autodesk.com/cloudhelp/2023/ENU/AutoCAD-AutoLISP-Reference/files/GUID-188B957C-4CDF-41C7-99BE-8080FA587F74.htm")

(setq *autolisp-reference-entry* (cons (cons 'url *autolisp-reference-value*) *autolisp-reference-entry*))

(setq *autolisp-reference-value* "Windows\n\n(vl-file-rename \"c:/newauto.bat\" \"c:/myauto.bat\")\nT\n\nMac OS\n\n(vl-file-rename \"/oldstartup.sh\" \"/mystartup.sh\")\nT")

(setq *autolisp-reference-entry* (cons (cons 'examples *autolisp-reference-value*) *autolisp-reference-entry*))

(setq *autolisp-reference-value* "AutoCAD 2021\n- old-filename\n- and\n- new-filename\n- arguments previously accepted ASCII text strings, but they now accept Unicode text strings.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: T or nil\nT, if renaming completed successfully; nil if renaming failed.\nNote: If the target file already exists, this function fails.")

(setq *autolisp-reference-entry* (cons (cons 'return-values *autolisp-reference-value*) *autolisp-reference-entry*))

(setq *autolisp-reference-value* nil)

(setq *autolisp-reference-string* "Type: String\nNew name to be assigned to the file.\nNote: If you do not specify a path name, vl-file-rename writes the renamed file to the AutoCAD default drawing directory.")

(setq *autolisp-reference-value* (cons (cons "new-filename" *autolisp-reference-string*) *autolisp-reference-value*))

(setq *autolisp-reference-string* "Type: String\nName of the file you want to rename. If you do not specify a full path name, vl-file-rename looks in the AutoCAD default drawing directory.")

(setq *autolisp-reference-value* (cons (cons "old-filename" *autolisp-reference-string*) *autolisp-reference-value*))

(setq *autolisp-reference-entry* (cons (cons 'arguments *autolisp-reference-value*) *autolisp-reference-entry*))

(setq *autolisp-reference-value* "(vl-file-rename old-filename new-filename)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Renames a file")

(setq *autolisp-reference-entry* (cons (cons 'summary *autolisp-reference-value*) *autolisp-reference-entry*))

(setq *autolisp-reference-value* "vl-file-rename (AutoLISP)")

(setq *autolisp-reference-entry* (cons (cons 'title *autolisp-reference-value*) *autolisp-reference-entry*))

(setq *autolisp-reference-value* "vl-file-rename")

(setq *autolisp-reference-entry* (cons (cons 'name *autolisp-reference-value*) *autolisp-reference-entry*))

(setq *autolisp-reference-parts* (cons (list (cons "vl-file-rename" *autolisp-reference-entry*)) *autolisp-reference-parts*))

(setq *autolisp-reference-entry* nil)

(setq *autolisp-reference-value* "GUID-646032BF-CAC1-4166-9EBA-2C954DFF3005")

(setq *autolisp-reference-entry* (cons (cons 'guid *autolisp-reference-value*) *autolisp-reference-entry*))

(setq *autolisp-reference-value* "https://help.autodesk.com/cloudhelp/2023/ENU/AutoCAD-AutoLISP-Reference/files/GUID-646032BF-CAC1-4166-9EBA-2C954DFF3005.htm")

(setq *autolisp-reference-entry* (cons (cons 'url *autolisp-reference-value*) *autolisp-reference-entry*))

(setq *autolisp-reference-value* "Windows\n\n(vl-file-size \"c:/autoexec.bat\")\n1417\n\n(vl-file-size \"c:/\")\n0\nIn the preceding example, vl-file-size returned 0 because c:/ names a directory.\n\nMac OS\n\n(vl-file-size \"/output.txt\")\n568\n\n(vl-file-size \"/\")\n0\nIn the preceding example, vl-file-size returned 0 because / names the <root> of the drive and not a file.")

(setq *autolisp-reference-entry* (cons (cons 'examples *autolisp-reference-value*) *autolisp-reference-entry*))

(setq *autolisp-reference-value* "AutoCAD 2021\n- filename\n- argument previously accepted an ASCII text string, but now accepts a Unicode text string.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: Integer\nIf successful, vl-file-size returns an integer showing the size of filename. If the file is not readable, vl-file-size returns nil. If filename is a directory or an empty file, vl-file-size returns 0.")

(setq *autolisp-reference-entry* (cons (cons 'return-values *autolisp-reference-value*) *autolisp-reference-entry*))

(setq *autolisp-reference-value* nil)

(setq *autolisp-reference-string* "Type: String\nNaming the file to be sized. If you do not specify a full path name, vl-file-size searches the AutoCAD default drawing directory for the file.")

(setq *autolisp-reference-value* (cons (cons "filename" *autolisp-reference-string*) *autolisp-reference-value*))

(setq *autolisp-reference-entry* (cons (cons 'arguments *autolisp-reference-value*) *autolisp-reference-entry*))

(setq *autolisp-reference-value* "(vl-file-size filename)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Determines the size of a file, in bytes")

(setq *autolisp-reference-entry* (cons (cons 'summary *autolisp-reference-value*) *autolisp-reference-entry*))

(setq *autolisp-reference-value* "vl-file-size (AutoLISP)")

(setq *autolisp-reference-entry* (cons (cons 'title *autolisp-reference-value*) *autolisp-reference-entry*))

(setq *autolisp-reference-value* "vl-file-size")

(setq *autolisp-reference-entry* (cons (cons 'name *autolisp-reference-value*) *autolisp-reference-entry*))

(setq *autolisp-reference-parts* (cons (list (cons "vl-file-size" *autolisp-reference-entry*)) *autolisp-reference-parts*))

(setq *autolisp-reference-entry* nil)

(setq *autolisp-reference-value* "GUID-7F6A31B2-7D51-4C4D-B239-206F398D67CA")

(setq *autolisp-reference-entry* (cons (cons 'guid *autolisp-reference-value*) *autolisp-reference-entry*))

(setq *autolisp-reference-value* "https://help.autodesk.com/cloudhelp/2023/ENU/AutoCAD-AutoLISP-Reference/files/GUID-7F6A31B2-7D51-4C4D-B239-206F398D67CA.htm")

(setq *autolisp-reference-entry* (cons (cons 'url *autolisp-reference-value*) *autolisp-reference-entry*))

(setq *autolisp-reference-value* "Windows\n\n(vl-file-systime\n  \"c:/program files/<AutoCAD installation directory>/sample/visuallisp/yinyang.lsp\")\n(1998 4 3 8 10 6 52)\nThe returned value shows that the file was last modified in 1998, in the 4th month of the year (April), the 3rd day of the week (Wednesday), on the 8th day of the month, at 10:6:52.\n\nMac OS\n\n(vl-file-systime \"/output.txt\")\n(2011 5 4 26 16 3 51 586)\nThe returned value shows that the file was last modified in 2011, in the 5th month of the year (May), the 4th day of the week (Thursday), on the 26th day of the month, at 4:03:51 PM.")

(setq *autolisp-reference-entry* (cons (cons 'examples *autolisp-reference-value*) *autolisp-reference-entry*))

(setq *autolisp-reference-value* "AutoCAD 2021\n- filename\n- argument previously accepted an ASCII text string, but now accepts a Unicode text string.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: List or nil\nA list containing the modification date and time; otherwise nil, if the file is not found.\nThe list returned contains the following elements:\n- year\n- month\n- day of week\n- day of month\n- hours\n- minutes\n- seconds\nNote: Monday is day 1 of day of week, Tuesday is day 2, and so on.")

(setq *autolisp-reference-entry* (cons (cons 'return-values *autolisp-reference-value*) *autolisp-reference-entry*))

(setq *autolisp-reference-value* nil)

(setq *autolisp-reference-string* "Type: String\nName of the file to be checked.")

(setq *autolisp-reference-value* (cons (cons "filename" *autolisp-reference-string*) *autolisp-reference-value*))

(setq *autolisp-reference-entry* (cons (cons 'arguments *autolisp-reference-value*) *autolisp-reference-entry*))

(setq *autolisp-reference-value* "(vl-file-systime filename)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns last modification time of the specified file")

(setq *autolisp-reference-entry* (cons (cons 'summary *autolisp-reference-value*) *autolisp-reference-entry*))

(setq *autolisp-reference-value* "vl-file-systime (AutoLISP)")

(setq *autolisp-reference-entry* (cons (cons 'title *autolisp-reference-value*) *autolisp-reference-entry*))

(setq *autolisp-reference-value* "vl-file-systime")

(setq *autolisp-reference-entry* (cons (cons 'name *autolisp-reference-value*) *autolisp-reference-entry*))

(setq *autolisp-reference-parts* (cons (list (cons "vl-file-systime" *autolisp-reference-entry*)) *autolisp-reference-parts*))

(setq *autolisp-reference-parts*
  (cons
    '(("vl-filename-base" .
          ((name . "vl-filename-base")
           (title . "vl-filename-base (AutoLISP)")
           (summary . "Returns the name of a file, after stripping out the directory path and extension")
           (source-kind . "AutoLISP")
           (alphabetic-group . "V")
           (feature-groups . ("File-Handling"))
           (supported-platforms . "Windows and Mac OS")
           (signature . "(vl-filename-base filename)")
           (arguments . (("filename" . "Type: String\nFile name. The vl-filename-base function does not check to see if the file exists.")))
           (return-values . "Type: String\nTextual value containing filename in uppercase, with any directory and extension stripped from the name.")
           (release-information . nil)
           (history . nil)
           (examples . "Windows\n\n(vl-filename-base \"c:\\\\acadwin\\\\acad.exe\")\n\"ACAD\"\n\n(vl-filename-base \"c:\\\\acadwin\")\n\"ACADWIN\"\n\nMac OS\n\n(vl-filename-base \"/myutilities/lsp/utilities.lsp\")\n\"utilities\"\n\n(vl-filename-base \"/myutilities/support\")\n\"support\"")
           (url . "https://help.autodesk.com/cloudhelp/2023/ENU/AutoCAD-AutoLISP-Reference/files/GUID-DA20B039-C252-4751-AA2F-EFC314E7D5A0.htm")
           (guid . "GUID-DA20B039-C252-4751-AA2F-EFC314E7D5A0"))))
    *autolisp-reference-parts*))

(setq *autolisp-reference-parts*
  (cons
    '(("vl-filename-directory" .
          ((name . "vl-filename-directory")
           (title . "vl-filename-directory (AutoLISP)")
           (summary . "Returns the directory path of a file, after stripping out the name and extension")
           (source-kind . "AutoLISP")
           (alphabetic-group . "V")
           (feature-groups . ("File-Handling"))
           (supported-platforms . "Windows and Mac OS")
           (signature . "(vl-filename-directory filename)")
           (arguments . (("filename" . "Type: String\nComplete file name, including the path. The vl-filename-directory function does not check to see if the specified file exists. Slashes (/) and backslashes (\\) are accepted as directory delimiters.")))
           (return-values . "Type: String\nA textual value containing the directory portion of filename, in uppercase.")
           (release-information . nil)
           (history . nil)
           (examples . "Windows\n\n(vl-filename-directory \"c:\\\\acadwin\\\\template.txt\")\n\"C:\\\\ACADWIN\"\n\n(vl-filename-directory \"template.txt\")\n\"\"\n\nMac OS\n\n(vl-filename-directory \"/myutilities/support/template.txt\")\n\"/myutilities/support\"\n\n(vl-filename-directory \"template.txt\")\n\"\"")
           (url . "https://help.autodesk.com/cloudhelp/2023/ENU/AutoCAD-AutoLISP-Reference/files/GUID-AAB7ED2B-C119-4B30-A831-71A4D02757B0.htm")
           (guid . "GUID-AAB7ED2B-C119-4B30-A831-71A4D02757B0"))))
    *autolisp-reference-parts*))

(setq *autolisp-reference-parts*
  (cons
    '(("vl-filename-extension" .
          ((name . "vl-filename-extension")
           (title . "vl-filename-extension (AutoLISP)")
           (summary . "Returns the extension from a file name, after stripping out the rest of the name")
           (source-kind . "AutoLISP")
           (alphabetic-group . "V")
           (feature-groups . ("File-Handling"))
           (supported-platforms . "Windows and Mac OS")
           (signature . "(vl-filename-extension filename)")
           (arguments . (("filename" . "Type: String\nFile name, including the extension. The vl-filename-extension function does not check to see if the specified file exists.")))
           (return-values . "Type: String or nil\nA string containing the extension of filename. The returned string starts with a period (.) and is in uppercase. If filename does not contain an extension, vl-filename-extension returns nil.")
           (release-information . nil)
           (history . nil)
           (examples . "Windows\n\n(vl-filename-extension \"c:\\\\acadwin\\\\output.txt\")\n\".txt\"\n\n(vl-filename-extension \"c:\\\\acadwin\\\\output\")\nnil\n\nMac OS\n\n(vl-filename-extension \"/myutilities/support/output.txt\")\n\".txt\"\n\n(vl-filename-extension \"/myutilities/support/output\")\nnil")
           (url . "https://help.autodesk.com/cloudhelp/2023/ENU/AutoCAD-AutoLISP-Reference/files/GUID-6AF5AC95-2E38-4D2C-8A81-8D26F7E80375.htm")
           (guid . "GUID-6AF5AC95-2E38-4D2C-8A81-8D26F7E80375"))))
    *autolisp-reference-parts*))

(setq *autolisp-reference-entry* nil)

(setq *autolisp-reference-value* "GUID-F417A5EF-95BB-47EE-B60E-7C017635580D")

(setq *autolisp-reference-entry* (cons (cons 'guid *autolisp-reference-value*) *autolisp-reference-entry*))

(setq *autolisp-reference-value* "https://help.autodesk.com/cloudhelp/2023/ENU/AutoCAD-AutoLISP-Reference/files/GUID-F417A5EF-95BB-47EE-B60E-7C017635580D.htm")

(setq *autolisp-reference-entry* (cons (cons 'url *autolisp-reference-value*) *autolisp-reference-entry*))

(setq *autolisp-reference-value* "Windows\n\n(vl-filename-mktemp)\n\"C:\\\\TMP\\\\$VL~~004\"\n\n(vl-filename-mktemp \"myapp.del\")\n\"C:\\\\TMP\\\\MYAPP005.DEL\"\n\n(vl-filename-mktemp \"c:\\\\acadwin\\\\myapp.del\")\n\"C:\\\\ACADWIN\\\\MYAPP006.DEL\"\n\n(vl-filename-mktemp \"c:\\\\acadwin\\\\myapp.del\")\n\"C:\\\\ACADWIN\\\\MYAPP007.DEL\"\n\n(vl-filename-mktemp \"myapp\" \"c:\\\\acadwin\")\n\"C:\\\\ACADWIN\\\\MYAPP008\"\n\n(vl-filename-mktemp \"myapp\" \"c:\\\\acadwin\" \".del\")\n\"C:\\\\ACADWIN\\\\MYAPP00A.DEL\"\n\nMac OS\n\n(vl-filename-mktemp)\n\"/documents/$VL~~001\"\n\n(vl-filename-mktemp \"myapp.del\")\n\"/documents/MYAPP002.DEL\"\n\n(vl-filename-mktemp \"/myutilities/temp/myapp.del\")\n\"/myutilities/temp/MYAPP003.DEL\"\n\n(vl-filename-mktemp \"/myutilities/temp/myapp.del\")\n\"/myutilities/temp/MYAPP004.DEL\"\n\n(vl-filename-mktemp \"myapp\" \"/myutilities/temp\")\n\"/myutilities/temp/MYAPP005\"\n\n(vl-filename")

(setq *autolisp-reference-value* (strcat *autolisp-reference-value* "-mktemp \"myapp\" \"/myutilities/temp\" \".del\")\n\"/myutilities/temp/MYAPP006.DEL\""))

(setq *autolisp-reference-entry* (cons (cons 'examples *autolisp-reference-value*) *autolisp-reference-entry*))

(setq *autolisp-reference-value* "AutoCAD 2021\n- pattern\n- ,\n- directory\n- and\n- extension\n- arguments previously accepted ASCII text strings, but they now accept Unicode text strings.\n- Return value was modified to support Unicode characters and might be different than earlier releases. For example,\n- (vl-filename-mktemp \"myapp\" \"c:\\\\abc中\")\n- previously returned a temporary file name in the path identified by the\n- directory\n- argument, but now correctly returns a temporary file name based on the directory provided to the function.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: String\nA textual value containing a file name, in the following format:\ndirectory\\base<XXX><.extension>\nwhere:\nbase is up to 5 characters, taken from pattern\nXXX is a 3-character unique combination\nAll file names generated by vl-filename-mktemp during a session are deleted when you exit the application.")

(setq *autolisp-reference-entry* (cons (cons 'return-values *autolisp-reference-value*) *autolisp-reference-entry*))

(setq *autolisp-reference-value* nil)

(setq *autolisp-reference-string* "Type: String\nExtension to be assigned to the file; if nil or absent, vl-filename-mktemp uses the extension part of pattern (which may be an empty string).")

(setq *autolisp-reference-value* (cons (cons "extension" *autolisp-reference-string*) *autolisp-reference-value*))

(setq *autolisp-reference-string* "Type: String\nDirectory for temporary files; if nil or absent, vl-filename-mktemp chooses a directory in the following order:\n- The directory specified in\n- pattern\n- , if any.\n- The directory specified in the TMP environment variable.\n- The directory specified in the TEMP environment variable.\n- The current directory.")

(setq *autolisp-reference-value* (cons (cons "directory" *autolisp-reference-string*) *autolisp-reference-value*))

(setq *autolisp-reference-string* "Type: String\nFile name pattern; if nil or absent, vl-filename-mktemp uses “$VL~~”.")

(setq *autolisp-reference-value* (cons (cons "pattern" *autolisp-reference-string*) *autolisp-reference-value*))

(setq *autolisp-reference-entry* (cons (cons 'arguments *autolisp-reference-value*) *autolisp-reference-entry*))

(setq *autolisp-reference-value* "(vl-filename-mktemp [pattern directory extension])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Calculates a unique file name to be used for a temporary file")

(setq *autolisp-reference-entry* (cons (cons 'summary *autolisp-reference-value*) *autolisp-reference-entry*))

(setq *autolisp-reference-value* "vl-filename-mktemp (AutoLISP)")

(setq *autolisp-reference-entry* (cons (cons 'title *autolisp-reference-value*) *autolisp-reference-entry*))

(setq *autolisp-reference-value* "vl-filename-mktemp")

(setq *autolisp-reference-entry* (cons (cons 'name *autolisp-reference-value*) *autolisp-reference-entry*))

(setq *autolisp-reference-parts* (cons (list (cons "vl-filename-mktemp" *autolisp-reference-entry*)) *autolisp-reference-parts*))

(setq *autolisp-reference-parts*
  (cons
    '(("vl-get-resource" .
          ((name . "vl-get-resource")
           (title . "vl-get-resource (AutoLISP/Visual LISP IDE)")
           (summary . "Returns the text stored in a .txt file packaged in a VLX")
           (source-kind . "AutoLISP/Visual LISP IDE")
           (alphabetic-group . "V")
           (feature-groups . nil)
           (supported-platforms . "Windows only")
           (signature . "(vl-get-resource text-file)")
           (arguments . (("text-file" . "Type: String\nName of a .txt file packaged with the VLX. Do not include the .txt extension when specifying the file name.")))
           (return-values . "Type: String\nA textual value containing the text in text-file.")
           (release-information . nil)
           (history . nil)
           (examples . "Assume the getres.vlx file contains a LISP program defining a function named print-readme, and a text file named readme.txt. The print-readme function is defined as follows:\n\n(defun print-readme ()\n   (princ (vl-get-resource \"readme\"))\n   (princ)\n)\n\nAfter loading getres.vlx, invoke print-readme:\n\n(print-readme)\nProduct Readme text\nProduct Readme text 2")
           (url . "https://help.autodesk.com/cloudhelp/2023/ENU/AutoCAD-AutoLISP-Reference/files/GUID-947B44CE-EAC4-4B17-83E1-8521AD5F5341.htm")
           (guid . "GUID-947B44CE-EAC4-4B17-83E1-8521AD5F5341"))))
    *autolisp-reference-parts*))

(setq *autolisp-reference-parts*
  (cons
    '(("vl-list*" .
          ((name . "vl-list*")
           (title . "vl-list* (AutoLISP)")
           (summary . "Constructs and returns a list")
           (source-kind . "AutoLISP")
           (alphabetic-group . "V")
           (feature-groups . ("List Manipulation"))
           (supported-platforms . "Windows and Mac OS")
           (signature . "(vl-list* object [object ...])")
           (arguments . (("object" . "Type: Integer, Real, String, List, File, Symbol, Ename (entity name), T, or nil\nAny LISP object.")))
           (return-values . "The vl-list* function is similar to list, but it will place the last object in the final cdr of the result list. If the last argument to vl-list* is an atom, the result is a dotted list. If the last argument is a list, its elements are appended to all previous arguments added to the constructed list. The possible return values from vl-list* are\n- An atom, if a single atom\n- object\n- is specified.\n- A dotted pair, if all\n- object\n- arguments are atoms.\n- A dotted list, if the last argument is an atom and neither of the previous conditions is true.\n- A list, if none of the previous statements is true.")
           (release-information . nil)
           (history . nil)
           (examples . "(vl-list* 1)\n1\n\n(vl-list* 0 \"text\")\n(0 . \"TEXT\")\n\n(vl-list* 1 2 3)\n(1 2 . 3)\n\n(vl-list* 1 2 '(3 4))\n(1 2 3 4)")
           (url . "https://help.autodesk.com/cloudhelp/2023/ENU/AutoCAD-AutoLISP-Reference/files/GUID-959DE11B-95E8-4AC3-BFBD-02406977D343.htm")
           (guid . "GUID-959DE11B-95E8-4AC3-BFBD-02406977D343"))))
    *autolisp-reference-parts*))

(setq *autolisp-reference-entry* nil)

(setq *autolisp-reference-value* "GUID-02C7058A-F648-48F5-BAF6-2A62EABD4DF6")

(setq *autolisp-reference-entry* (cons (cons 'guid *autolisp-reference-value*) *autolisp-reference-entry*))

(setq *autolisp-reference-value* "https://help.autodesk.com/cloudhelp/2023/ENU/AutoCAD-AutoLISP-Reference/files/GUID-02C7058A-F648-48F5-BAF6-2A62EABD4DF6.htm")

(setq *autolisp-reference-entry* (cons (cons 'url *autolisp-reference-value*) *autolisp-reference-entry*))

(setq *autolisp-reference-value* nil)

(setq *autolisp-reference-entry* (cons (cons 'examples *autolisp-reference-value*) *autolisp-reference-entry*))

(setq *autolisp-reference-value* "AutoCAD 2021\n- char-codes-list\n- argument previously accepted integers in the range of 1-255, but now accepts integers in the range of 1-65536.\n- Return value was modified to support Unicode characters and might be different than earlier releases. For example,\n- (vl-list->string (list 49 128))\n- previously returned \"1€\", but now returns \"1\". If you want to return \"1€\", your code will need to be updated to\n- (vl-list->string (list 49 8364))\n- .\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: String\nA textual value consisting of characters, with each character based on one of the integers supplied in char-codes-list.")

(setq *autolisp-reference-entry* (cons (cons 'return-values *autolisp-reference-value*) *autolisp-reference-entry*))

(setq *autolisp-reference-value* nil)

(setq *autolisp-reference-string* "Type: List\nA list of non-negative integers. Each integer must be in the range of 1-65536.")

(setq *autolisp-reference-value* (cons (cons "char-codes-list" *autolisp-reference-string*) *autolisp-reference-value*))

(setq *autolisp-reference-entry* (cons (cons 'arguments *autolisp-reference-value*) *autolisp-reference-entry*))

(setq *autolisp-reference-value* "(vl-list->string char-codes-list)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("List Manipulation"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Combines the characters associated with a list of integers into a string")

(setq *autolisp-reference-entry* (cons (cons 'summary *autolisp-reference-value*) *autolisp-reference-entry*))

(setq *autolisp-reference-value* "vl-list->string (AutoLISP)")

(setq *autolisp-reference-entry* (cons (cons 'title *autolisp-reference-value*) *autolisp-reference-entry*))

(setq *autolisp-reference-value* "vl-list->string")

(setq *autolisp-reference-entry* (cons (cons 'name *autolisp-reference-value*) *autolisp-reference-entry*))

(setq *autolisp-reference-parts* (cons (list (cons "vl-list->string" *autolisp-reference-entry*)) *autolisp-reference-parts*))

(setq *autolisp-reference-parts*
  (cons
    '(("vl-list-exported-functions" .
          ((name . "vl-list-exported-functions")
           (title . "vl-list-exported-functions (AutoLISP/Visual LISP IDE)")
           (summary . "Lists exported functions")
           (source-kind . "AutoLISP/Visual LISP IDE")
           (alphabetic-group . "V")
           (feature-groups . ("VLX Namespace"))
           (supported-platforms . "Windows only")
           (signature . "(vl-list-exported-functions [appname])")
           (arguments . (("appname" . "Type: String\nName of a loaded VLX application. Do not include the .vlx extension.")))
           (return-values . "Type: List\nA list of strings naming exported functions; otherwise nil, if there are no functions exported from the specified VLX. If appname is omitted or is nil, vl-list-exported-functions returns a list of all exported functions (for example, c: functions) except those exported from VLX namespaces.")
           (release-information . nil)
           (history . nil)
           (examples . "(vl-list-exported-functions \"whichexpns\")\n(\"WHICHNAMESPACE\")")
           (url . "https://help.autodesk.com/cloudhelp/2023/ENU/AutoCAD-AutoLISP-Reference/files/GUID-3D87AA2E-DB4B-4B28-B5A8-04A8183BF8AD.htm")
           (guid . "GUID-3D87AA2E-DB4B-4B28-B5A8-04A8183BF8AD"))))
    *autolisp-reference-parts*))

(setq *autolisp-reference-parts*
  (cons
    '(("vl-list-length" .
          ((name . "vl-list-length")
           (title . "vl-list-length (AutoLISP)")
           (summary . "Calculates list length of a true list")
           (source-kind . "AutoLISP")
           (alphabetic-group . "V")
           (feature-groups . ("List Manipulation"))
           (supported-platforms . "Windows and Mac OS")
           (signature . "(vl-list-length list-or-cons-object)")
           (arguments . (("list-or-cons-object" . "Type: List or nil\nA true or dotted list.")))
           (return-values . "Type: Integer or nil\nAn integer containing the list length if the argument is a true list; otherwise nil if list-or-cons-object is a dotted list.\nCompatibility note: The vl-list-length function returns nil for a dotted list, while the corresponding Common LISP function issues an error message if the argument is a dotted list.")
           (release-information . nil)
           (history . nil)
           (examples . "(vl-list-length nil)\n0\n\n(vl-list-length '(1 2))\n2\n\n(vl-list-length '(1 2 . 3))\nnil")
           (url . "https://help.autodesk.com/cloudhelp/2023/ENU/AutoCAD-AutoLISP-Reference/files/GUID-5BAF3505-B1E9-49BF-9202-AAD36043B6D3.htm")
           (guid . "GUID-5BAF3505-B1E9-49BF-9202-AAD36043B6D3"))))
    *autolisp-reference-parts*))

(setq *autolisp-reference-entry* nil)

(setq *autolisp-reference-value* "GUID-0F0C7A45-41AA-410F-AEF0-EECAE812FCF3")

(setq *autolisp-reference-entry* (cons (cons 'guid *autolisp-reference-value*) *autolisp-reference-entry*))

(setq *autolisp-reference-value* "https://help.autodesk.com/cloudhelp/2023/ENU/AutoCAD-AutoLISP-Reference/files/GUID-0F0C7A45-41AA-410F-AEF0-EECAE812FCF3.htm")

(setq *autolisp-reference-entry* (cons (cons 'url *autolisp-reference-value*) *autolisp-reference-entry*))

(setq *autolisp-reference-value* "Test for loaded VLX files associated with the current AutoCAD document:\n\n(vl-list-loaded-vlx)\nnil\n\nNo VLX files are associated with the current document.\n\nLoad two VLX files; both VLX applications have been compiled to run in their own namespace:\n\n(load \"c:/my documents/visual lisp/examples/foo1.vlx\")\nnil\n\n(load \"c:/my documents/visual lisp/examples/foo2.vlx\")\nnil\n\nTest for loaded VLX files associated with the current AutoCAD document:\n\n(vl-list-loaded-vlx)\n(FOO1 FOO2)\n\nThe two VLX files just loaded are identified by vl-list-loaded-vlx.\n\nLoad a VLX that was compiled to run in a document's namespace:\n\n(load \"c:/my documents/visual lisp/examples/foolocal.vlx\")\nnil\n\nTest for loaded VLX files:\n\n(vl-list-loaded-vlx)\n(FOO1 FOO2))\n\nThe last VLX loaded (foolocal.vlx) is not returned by vl-list-loaded-vlx because the application was loaded into the document's")

(setq *autolisp-reference-value* (strcat *autolisp-reference-value* " namespace; the VLX does not have its own namespace."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nA list of symbols identifying separate-namespace VLX applications associated with the current AutoCAD document; otherwise nil, if there are no VLX applications associated with the current document.\nThe vl-list-loaded-vlx function does not identify VLX applications that are loaded in the current document's namespace.")

(setq *autolisp-reference-entry* (cons (cons 'return-values *autolisp-reference-value*) *autolisp-reference-entry*))

(setq *autolisp-reference-value* nil)

(setq *autolisp-reference-entry* (cons (cons 'arguments *autolisp-reference-value*) *autolisp-reference-entry*))

(setq *autolisp-reference-value* "(vl-list-loaded-vlx)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("VLX Namespace"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns a list of all separate-namespace VLX files associated with the current document")

(setq *autolisp-reference-entry* (cons (cons 'summary *autolisp-reference-value*) *autolisp-reference-entry*))

(setq *autolisp-reference-value* "vl-list-loaded-vlx (AutoLISP)")

(setq *autolisp-reference-entry* (cons (cons 'title *autolisp-reference-value*) *autolisp-reference-entry*))

(setq *autolisp-reference-value* "vl-list-loaded-vlx")

(setq *autolisp-reference-entry* (cons (cons 'name *autolisp-reference-value*) *autolisp-reference-entry*))

(setq *autolisp-reference-parts* (cons (list (cons "vl-list-loaded-vlx" *autolisp-reference-entry*)) *autolisp-reference-parts*))

(setq *autolisp-reference-parts*
  (cons
    '(("vl-load-all" .
          ((name . "vl-load-all")
           (title . "vl-load-all (AutoLISP)")
           (summary . "Loads a file into all open AutoCAD documents, and into any document subsequently opened during the current AutoCAD session")
           (source-kind . "AutoLISP")
           (alphabetic-group . "V")
           (feature-groups . ("Application-Handling" "Namespace Communication"))
           (supported-platforms . "Windows and Mac OS")
           (signature . nil)
           (arguments . nil)
           (return-values . "Type: nil or error\nnil if successful; otherwise, an error occurs when filename is not found.")
           (release-information . nil)
           (history . nil)
           (examples . "Windows\n\n(vl-load-all \"c:/my documents/visual lisp/examples/whichns.lsp\")\nnil\n\n(vl-load-all \"yinyang.lsp\")\nnil\n\nMac OS\n\n(vl-load-all \"/myutilities/lsp/utilities.lsp\")\nnil\n\n(vl-load-all \"utilities.lsp\")\nnil")
           (url . "https://help.autodesk.com/cloudhelp/2023/ENU/AutoCAD-AutoLISP-Reference/files/GUID-116F4D02-4B1A-4298-B38C-5B38FD982867.htm")
           (guid . "GUID-116F4D02-4B1A-4298-B38C-5B38FD982867"))))
    *autolisp-reference-parts*))

(setq *autolisp-reference-parts*
  (cons
    '(("vl-load-com" .
          ((name . "vl-load-com")
           (title . "vl-load-com (AutoLISP/ActiveX)")
           (summary . "Loads the extended AutoLISP functions related to ActiveX support")
           (source-kind . "AutoLISP/ActiveX")
           (alphabetic-group . "V")
           (feature-groups . ("Reactor Functions Reference (AutoLISP/ActiveX)"))
           (supported-platforms . "Windows only")
           (signature . "(vl-load-com)")
           (arguments . nil)
           (return-values . "Type: nil\nAlways returns nil.")
           (release-information . nil)
           (history . nil)
           (examples . "N/A")
           (url . "https://help.autodesk.com/cloudhelp/2023/ENU/AutoCAD-AutoLISP-Reference/files/GUID-6C7A8632-C12F-42BD-909E-68D804863AE2.htm")
           (guid . "GUID-6C7A8632-C12F-42BD-909E-68D804863AE2"))))
    *autolisp-reference-parts*))

(setq *autolisp-reference-parts*
  (cons
    '(("vl-load-reactors" .
          ((name . "vl-load-reactors")
           (title . "vl-load-reactors (AutoLISP/ActiveX)")
           (summary . "Loads reactor support functions")
           (source-kind . "AutoLISP/ActiveX")
           (alphabetic-group . "V")
           (feature-groups . nil)
           (supported-platforms . "Windows only")
           (signature . "(vl-load-reactors)")
           (arguments . nil)
           (return-values . "Type: nil\nAlways returns nil.")
           (release-information . nil)
           (history . nil)
           (examples . "N/A")
           (url . "https://help.autodesk.com/cloudhelp/2023/ENU/AutoCAD-AutoLISP-Reference/files/GUID-05F7E56E-51C7-43E2-B1F5-6CD55C74EE8E.htm")
           (guid . "GUID-05F7E56E-51C7-43E2-B1F5-6CD55C74EE8E"))))
    *autolisp-reference-parts*))

(setq *autolisp-reference-entry* nil)

(setq *autolisp-reference-value* "GUID-CFEA98F0-F6DE-4FF4-839A-0F6C8FBE1319")

(setq *autolisp-reference-entry* (cons (cons 'guid *autolisp-reference-value*) *autolisp-reference-entry*))

(setq *autolisp-reference-value* "https://help.autodesk.com/cloudhelp/2023/ENU/AutoCAD-AutoLISP-Reference/files/GUID-CFEA98F0-F6DE-4FF4-839A-0F6C8FBE1319.htm")

(setq *autolisp-reference-entry* (cons (cons 'url *autolisp-reference-value*) *autolisp-reference-entry*))

(setq *autolisp-reference-value* "The following command draws a line:\n\n(command \"._line\" '(0 10) '(30 50) nil)\nnil\n\nThe following command uses vl-member-if to return association lists describing an entity, if the entity is a line:\n\n(vl-member-if\n  '(lambda (x) (= (cdr x) \"AcDbLine\"))\n   (entget (entlast)))\n((100 . \"AcDbLine\") (10 0.0 10.0 0.0) (11 30.0 50.0 0.0) (210 0.0 0.0 1.0))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nA list, starting with the first element that passes the test and containing all elements following this in the original argument. If none of the elements passes the test condition, vl-member-if returns nil.")

(setq *autolisp-reference-entry* (cons (cons 'return-values *autolisp-reference-value*) *autolisp-reference-entry*))

(setq *autolisp-reference-value* nil)

(setq *autolisp-reference-string* "Type: List\nA list to be tested.")

(setq *autolisp-reference-value* (cons (cons "lst" *autolisp-reference-string*) *autolisp-reference-value*))

(setq *autolisp-reference-string* "Type: Subroutine or Symbol\nThe test function. This can be any function that accepts a single argument and returns T for any user-specified condition. The predicate-function value can take one of the following forms:\n- A symbol (function name)\n- '(LAMBDA (A1 A2) ...)\n- (FUNCTION (LAMBDA (A1 A2) ...))")

(setq *autolisp-reference-value* (cons (cons "predicate-function" *autolisp-reference-string*) *autolisp-reference-value*))

(setq *autolisp-reference-entry* (cons (cons 'arguments *autolisp-reference-value*) *autolisp-reference-entry*))

(setq *autolisp-reference-value* "(vl-member-if predicate-function lst)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("List Manipulation"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Determines if the predicate is true for one of the list members")

(setq *autolisp-reference-entry* (cons (cons 'summary *autolisp-reference-value*) *autolisp-reference-entry*))

(setq *autolisp-reference-value* "vl-member-if (AutoLISP)")

(setq *autolisp-reference-entry* (cons (cons 'title *autolisp-reference-value*) *autolisp-reference-entry*))

(setq *autolisp-reference-value* "vl-member-if")

(setq *autolisp-reference-entry* (cons (cons 'name *autolisp-reference-value*) *autolisp-reference-entry*))

(setq *autolisp-reference-parts* (cons (list (cons "vl-member-if" *autolisp-reference-entry*)) *autolisp-reference-parts*))

(setq *autolisp-reference-parts*
  (cons
    '(("vl-member-if-not" .
          ((name . "vl-member-if-not")
           (title . "vl-member-if-not (AutoLISP)")
           (summary . "Determines if the predicate is nil for one of the list members")
           (source-kind . "AutoLISP")
           (alphabetic-group . "V")
           (feature-groups . ("List Manipulation"))
           (supported-platforms . "Windows and Mac OS")
           (signature . "(vl-member-if-not predicate-function lst)")
           (arguments . (("predicate-function" . "Type: Subroutine or Symbol\nThe test function. This can be any function that accepts a single argument and returns T for any user-specified condition. The predicate-function value can take one of the following forms:\n- A symbol (function name)\n- '(LAMBDA (A1 A2) ...)\n- (FUNCTION (LAMBDA (A1 A2) ...))")
                           ("lst" . "Type: List\nA list to be tested.")))
           (return-values . "Type: List or nil\nA list, starting with the first element that fails the test and containing all elements following this in the original argument. If none of the elements fails the test condition, vl-member-if-not returns nil.")
           (release-information . nil)
           (history . nil)
           (examples . "(vl-member-if-not 'atom '(1 \"Str\" (0 . \"line\") nil t))\n((0 . \"line\") nil T)")
           (url . "https://help.autodesk.com/cloudhelp/2023/ENU/AutoCAD-AutoLISP-Reference/files/GUID-27EA5788-B68D-4302-900F-9D99902025E4.htm")
           (guid . "GUID-27EA5788-B68D-4302-900F-9D99902025E4"))))
    *autolisp-reference-parts*))

(setq *autolisp-reference-parts*
  (cons
    '(("vl-mkdir" .
          ((name . "vl-mkdir")
           (title . "vl-mkdir (AutoLISP)")
           (summary . "Creates a directory")
           (source-kind . "AutoLISP")
           (alphabetic-group . "V")
           (feature-groups . nil)
           (supported-platforms . "Windows and Mac OS")
           (signature . "(vl-mkdir directoryname)")
           (arguments . (("directoryname" . "Type: String\nThe name of the directory you want to create.")))
           (return-values . "Type: T or nil\nT if successful, nil if the directory exists or if unsuccessful.")
           (release-information . "Releases:\n- AutoCAD R14 and later on Windows\n- AutoCAD 2011 and later on Mac OS")
           (history . "AutoCAD 2021\n- directoryname\n- argument previously accepted an ASCII text string, but now accepts a Unicode text string.\n- LISPSYS system variable controls which AutoLISP engine is used and the behavior of the function.\n-   - 0 - ASCII character support (legacy behavior)\n-   - 1 or 2 - Unicode character support\n- Note: After the value of the LISPSYS system variable has been changed, AutoCAD must be restarted for the change to take affect.")
           (examples . "Windows\n\n(vl-mkdir \"c:\\\\mydirectory\")\nT\n\nMac OS\n\n(vl-mkdir \"/mydirectory\")\nT")
           (url . "https://help.autodesk.com/cloudhelp/2023/ENU/AutoCAD-AutoLISP-Reference/files/GUID-02D5CC9E-9394-4630-AE14-133F5F03D7B1.htm")
           (guid . "GUID-02D5CC9E-9394-4630-AE14-133F5F03D7B1"))))
    *autolisp-reference-parts*))

(setq *autolisp-reference-parts*
  (cons
    '(("vl-position" .
          ((name . "vl-position")
           (title . "vl-position (AutoLISP)")
           (summary . "Returns the index of the specified list item")
           (source-kind . "AutoLISP")
           (alphabetic-group . "V")
           (feature-groups . ("List Manipulation"))
           (supported-platforms . "Windows and Mac OS")
           (signature . "(vl-position symbol list)")
           (arguments . (("symbol" . "Type: Integer, Real, String, File, Symbol, Ename (entity name), T, or nil\nAny AutoLISP symbol.")
                           ("list" . "Type: List\nA true list.")))
           (return-values . "Type: Integer or nil\nA numeric value containing the index position of symbol in list; otherwise nil if symbol does not exist in the list.\nNote: The first list element is index 0, the second element is index 1, and so on.")
           (release-information . nil)
           (history . nil)
           (examples . "(setq stuff (list \"a\" \"b\" \"c\" \"d\" \"e\"))\n(\"a\" \"b\" \"c\" \"d\" \"e\")\n\n(vl-position \"c\" stuff)\n2")
           (url . "https://help.autodesk.com/cloudhelp/2023/ENU/AutoCAD-AutoLISP-Reference/files/GUID-E2C60C39-B46E-4779-82CE-CFFCCCE93AF0.htm")
           (guid . "GUID-E2C60C39-B46E-4779-82CE-CFFCCCE93AF0"))))
    *autolisp-reference-parts*))

(setq *autolisp-reference-parts*
  (cons
    '(("vl-prin1-to-string" .
          ((name . "vl-prin1-to-string")
           (title . "vl-prin1-to-string (AutoLISP)")
           (summary . "Returns the string representation of LISP data as if it were output by the prin1 function")
           (source-kind . "AutoLISP")
           (alphabetic-group . "V")
           (feature-groups . ("String-Handling"))
           (supported-platforms . "Windows and Mac OS")
           (signature . "(vl-prin1-to-string data)")
           (arguments . (("data" . "Type: Integer, Real, String, List, Ename (entity name), T, or nil\nAny AutoLISP data.")))
           (return-values . "Type: String\nA textual value containing the printed representation of data as if displayed by prin1.")
           (release-information . nil)
           (history . nil)
           (examples . "Windows\n\n(vl-prin1-to-string \"abc\")\n\"\\\"abc\\\"\"\n\n(vl-prin1-to-string \"c:\\\\acadwin\")\n\"\\\"C:\\\\\\\\ACADWIN\\\"\"\n\n(vl-prin1-to-string 'my-var)\n\"MY-VAR\"\n\nMac OS\n\n(vl-prin1-to-string \"abc\")\n\"\\\"abc\\\"\"\n\n(vl-prin1-to-string \"/myutilities\")\n\"\\\"/myutilities\\\"\"\n\n(vl-prin1-to-string 'my-var)\n\"MY-VAR\"")
           (url . "https://help.autodesk.com/cloudhelp/2023/ENU/AutoCAD-AutoLISP-Reference/files/GUID-4AA25012-28D5-4723-8AD3-B8BF9AE62425.htm")
           (guid . "GUID-4AA25012-28D5-4723-8AD3-B8BF9AE62425"))))
    *autolisp-reference-parts*))

(setq *autolisp-reference-parts*
  (cons
    '(("vl-princ-to-string" .
          ((name . "vl-princ-to-string")
           (title . "vl-princ-to-string (AutoLISP)")
           (summary . "Returns the string representation of LISP data as if it were output by the princ function")
           (source-kind . "AutoLISP")
           (alphabetic-group . "V")
           (feature-groups . ("String-Handling"))
           (supported-platforms . "Windows and Mac OS")
           (signature . "(vl-princ-to-string data)")
           (arguments . (("data" . "Type: Integer, Real, String, List, Ename (entity name), T, or nil\nAny AutoLISP data.")))
           (return-values . "Type: String\nA string containing the printed representation of data as if displayed by princ.")
           (release-information . nil)
           (history . nil)
           (examples . "Windows\n\n(vl-princ-to-string \"abc\")\n\"abc\"\n\n(vl-princ-to-string \"c:\\\\acadwin\")\n\"C:\\\\ACADWIN\"\n\n(vl-princ-to-string 'my-var)\n\"MY-VAR\"\n\nMac OS\n\n(vl-princ-to-string \"abc\")\n\"abc\"\n\n(vl-princ-to-string \"/myutilities\")\n\"/myutilities\"\n\n(vl-princ-to-string 'my-var)\n\"MY-VAR\"")
           (url . "https://help.autodesk.com/cloudhelp/2023/ENU/AutoCAD-AutoLISP-Reference/files/GUID-33B0CA43-84F2-46DE-88BE-8FFF22C83FAD.htm")
           (guid . "GUID-33B0CA43-84F2-46DE-88BE-8FFF22C83FAD"))))
    *autolisp-reference-parts*))

(setq *autolisp-reference-parts*
  (cons
    '(("vl-propagate" .
          ((name . "vl-propagate")
           (title . "vl-propagate (AutoLISP)")
           (summary . "Copies the value of a variable into all open document namespaces (and sets its value in any subsequent drawings opened during the current AutoCAD session)")
           (source-kind . "AutoLISP")
           (alphabetic-group . "V")
           (feature-groups . ("Namespace Communication"))
           (supported-platforms . "Windows and Mac OS")
           (signature . "(vl-propagate 'symbol)")
           (arguments . (("symbol" . "Type: Symbol\nA symbol naming an AutoLISP variable.")))
           (return-values . "Type: nil\nAlways returns nil.")
           (release-information . nil)
           (history . nil)
           (examples . "(vl-propagate 'radius)\nnil")
           (url . "https://help.autodesk.com/cloudhelp/2023/ENU/AutoCAD-AutoLISP-Reference/files/GUID-9B30560A-5037-4C2D-8175-429E110277F5.htm")
           (guid . "GUID-9B30560A-5037-4C2D-8175-429E110277F5"))))
    *autolisp-reference-parts*))

(setq *autolisp-reference-parts*
  (cons
    '(("vl-registry-delete" .
          ((name . "vl-registry-delete")
           (title . "vl-registry-delete (AutoLISP)")
           (summary . "Deletes the specified key from the Windows Registry or property list file on Mac OS")
           (source-kind . "AutoLISP")
           (alphabetic-group . "V")
           (feature-groups . ("Windows Registry and Property List File"))
           (supported-platforms . "Windows and Mac OS")
           (signature . "(vl-registry-delete reg-key [val-name])")
           (arguments . (("reg-key" . "Type: String\nWindows registry key or property list file key on Mac OS.")
                           ("val-name" . "Type: String\nValue of the reg-key entry.")))
           (return-values . "Type: T or nil\nT if successful; otherwise nil.")
           (release-information . nil)
           (history . nil)
           (examples . "(vl-registry-write \"HKEY_CURRENT_USER\\\\Test\" \"\" \"test data\")\n\"test data\"\n\n(vl-registry-read \"HKEY_CURRENT_USER\\\\Test\")\n\"test data\"\n\n(vl-registry-delete \"HKEY_CURRENT_USER\\\\Test\")\nT")
           (url . "https://help.autodesk.com/cloudhelp/2023/ENU/AutoCAD-AutoLISP-Reference/files/GUID-BF5FB9C5-A015-464C-A475-B320C5B5E96C.htm")
           (guid . "GUID-BF5FB9C5-A015-464C-A475-B320C5B5E96C"))))
    *autolisp-reference-parts*))

(setq *autolisp-reference-parts*
  (cons
    '(("vl-registry-descendents" .
          ((name . "vl-registry-descendents")
           (title . "vl-registry-descendents (AutoLISP)")
           (summary . "Returns a list of subkeys or value names for the specified key of the Windows Registry or property list file on Mac OS")
           (source-kind . "AutoLISP")
           (alphabetic-group . "V")
           (feature-groups . ("Windows Registry and Property List File"))
           (supported-platforms . "Windows and Mac OS")
           (signature . "(vl-registry-descendents reg-key [val-names])")
           (arguments . (("reg-key" . "Type: String\nWindows registry key or property list file key on Mac OS.")
                           ("val-names" . "Type: String\nValues for the reg-key entry.")))
           (return-values . "Type: List or nil\nA list of strings, if successful; otherwise nil.")
           (release-information . nil)
           (history . nil)
           (examples . "(vl-registry-descendents \"HKEY_LOCAL_MACHINE\\\\SOFTWARE\")\n(\"Description\" \"Program Groups\" \"ORACLE\" \"ODBC\" \"Netscape\" \"Microsoft\")")
           (url . "https://help.autodesk.com/cloudhelp/2023/ENU/AutoCAD-AutoLISP-Reference/files/GUID-3A2A4AA0-8799-4B0A-AD26-443A8B4DD9BE.htm")
           (guid . "GUID-3A2A4AA0-8799-4B0A-AD26-443A8B4DD9BE"))))
    *autolisp-reference-parts*))

(setq *autolisp-reference-parts*
  (cons
    '(("vl-registry-read" .
          ((name . "vl-registry-read")
           (title . "vl-registry-read (AutoLISP)")
           (summary . "Returns data stored by a specific key/value pair in the Windows Registry or property list file on Mac OS")
           (source-kind . "AutoLISP")
           (alphabetic-group . "V")
           (feature-groups . ("Windows Registry and Property List File"))
           (supported-platforms . "Windows and Mac OS")
           (signature . "(vl-registry-read reg-key [val-name])")
           (arguments . (("reg-key" . "Type: String\nWindows registry key or property list file key on Mac OS.")
                           ("val-name" . "Type: String\nDefault value for the reg-key entry if it does not exist.")))
           (return-values . "Type: String or nil\nA string containing the data stored in the key, if successful; otherwise nil.")
           (release-information . nil)
           (history . nil)
           (examples . "(vl-registry-read \"HKEY_CURRENT_USER\\\\Test\")\nnil\n\n(vl-registry-write \"HKEY_CURRENT_USER\\\\Test\" \"\" \"test data\")\n\"test data\"\n\n(vl-registry-read \"HKEY_CURRENT_USER\\\\Test\")\n\"test data\"")
           (url . "https://help.autodesk.com/cloudhelp/2023/ENU/AutoCAD-AutoLISP-Reference/files/GUID-0B9E26CF-2410-482E-B568-7FE05B9F013C.htm")
           (guid . "GUID-0B9E26CF-2410-482E-B568-7FE05B9F013C"))))
    *autolisp-reference-parts*))

(setq *autolisp-reference-parts*
  (cons
    '(("vl-registry-write" .
          ((name . "vl-registry-write")
           (title . "vl-registry-write (AutoLISP)")
           (summary . "Creates a key in the Windows Registry or property list file on Mac OS")
           (source-kind . "AutoLISP")
           (alphabetic-group . "V")
           (feature-groups . ("Windows Registry and Property List File"))
           (supported-platforms . "Windows and Mac OS")
           (signature . "(vl-registry-write reg-key [val-name val-data])")
           (arguments . (("reg-key" . "Type: String\nWindows registry key or property list file key on Mac OS.\nNote: You cannot use vl-registry-write for HKEY_USERS or KEY_LOCAL_MACHINE.")
                           ("val-name" . "Type: String\nValue name for the key.")
                           ("val-data" . "Type: String\nData for the value name.")))
           (return-values . "Type: String or nil\nvl-registry-write returns val-data, if successful; otherwise nil.")
           (release-information . nil)
           (history . nil)
           (examples . "(vl-registry-write \"HKEY_CURRENT_USER\\\\Test\" \"\" \"test data\")\n\"test data\"\n\n(vl-registry-read \"HKEY_CURRENT_USER\\\\Test\")\n\"test data\"")
           (url . "https://help.autodesk.com/cloudhelp/2023/ENU/AutoCAD-AutoLISP-Reference/files/GUID-9DDE1962-43C5-40D2-85E3-B7A729CAB157.htm")
           (guid . "GUID-9DDE1962-43C5-40D2-85E3-B7A729CAB157"))))
    *autolisp-reference-parts*))

(setq *autolisp-reference-parts*
  (cons
    '(("vl-remove" .
          ((name . "vl-remove")
           (title . "vl-remove (AutoLISP)")
           (summary . "Removes elements from a list")
           (source-kind . "AutoLISP")
           (alphabetic-group . "V")
           (feature-groups . ("List Manipulation"))
           (supported-platforms . "Windows and Mac OS")
           (signature . "(vl-remove element-to-remove lst)")
           (arguments . (("element-to-remove" . "Type: Integer, Real, String, List, File, Ename (entity name), T, or nil\nThe value of the element to be removed; may be any LISP data type.")
                           ("lst" . "Type: List\nAny list.")))
           (return-values . "Type: List or nil\nThe lst with all elements except those equal to element-to-remove.")
           (release-information . nil)
           (history . nil)
           (examples . "(vl-remove pi (list pi t 0 \"abc\"))\n(T 0 \"abc\")")
           (url . "https://help.autodesk.com/cloudhelp/2023/ENU/AutoCAD-AutoLISP-Reference/files/GUID-1BF33827-5C9C-49B2-A21B-656E0F429B21.htm")
           (guid . "GUID-1BF33827-5C9C-49B2-A21B-656E0F429B21"))))
    *autolisp-reference-parts*))

(setq *autolisp-reference-parts*
  (cons
    '(("vl-remove-if" .
          ((name . "vl-remove-if")
           (title . "vl-remove-if (AutoLISP)")
           (summary . "Returns all elements of the supplied list that fail the test function")
           (source-kind . "AutoLISP")
           (alphabetic-group . "V")
           (feature-groups . ("List Manipulation"))
           (supported-platforms . "Windows and Mac OS")
           (signature . "(vl-remove-if predicate-function lst)")
           (arguments . (("predicate-function" . "Type: Subroutine or Symbol\nThe test function. This can be any function that accepts a single argument and returns T for any user-specified condition. The predicate-function value can take one of the following forms:\n- A symbol (function name)\n- '(LAMBDA (A1 A2) ...)\n- (FUNCTION (LAMBDA (A1 A2) ...))")
                           ("lst" . "Type: List\nA list to be tested.")))
           (return-values . "Type: List or nil\nA list containing all elements of lst for which predicate-function returns nil.")
           (release-information . nil)
           (history . nil)
           (examples . "(vl-remove-if 'vl-symbolp (list pi t 0 \"abc\"))\n(3.14159 0 \"abc\")")
           (url . "https://help.autodesk.com/cloudhelp/2023/ENU/AutoCAD-AutoLISP-Reference/files/GUID-9934F630-4697-47BA-84E6-A0430A3346EE.htm")
           (guid . "GUID-9934F630-4697-47BA-84E6-A0430A3346EE"))))
    *autolisp-reference-parts*))

(setq *autolisp-reference-parts*
  (cons
    '(("vl-remove-if-not" .
          ((name . "vl-remove-if-not")
           (title . "vl-remove-if-not (AutoLISP)")
           (summary . "Returns all elements of the supplied list that pass the test function")
           (source-kind . "AutoLISP")
           (alphabetic-group . "V")
           (feature-groups . ("List Manipulation"))
           (supported-platforms . "Windows and Mac OS")
           (signature . "(vl-remove-if-not predicate-function lst)")
           (arguments . (("predicate-function" . "Type: Subroutine or Symbol\nThe test function. This can be any function that accepts a single argument and returns T for any user-specified condition. The predicate-function value can take one of the following forms:\n- A symbol (function name)\n- '(LAMBDA (A1 A2) ...)\n- (FUNCTION (LAMBDA (A1 A2) ...))")
                           ("lst" . "Type: List\nA list to be tested.")))
           (return-values . "Type: List or nil\nA list containing all elements of lst for which predicate-function returns a non-nil value")
           (release-information . nil)
           (history . nil)
           (examples . "(vl-remove-if-not 'vl-symbolp (list pi t 0 \"abc\"))\n(T)")
           (url . "https://help.autodesk.com/cloudhelp/2023/ENU/AutoCAD-AutoLISP-Reference/files/GUID-53D12042-8DE3-4DAA-83BD-8ABB376ACA97.htm")
           (guid . "GUID-53D12042-8DE3-4DAA-83BD-8ABB376ACA97"))))
    *autolisp-reference-parts*))

(setq *autolisp-reference-parts*
  (cons
    '(("vl-some" .
          ((name . "vl-some")
           (title . "vl-some (AutoLISP)")
           (summary . "Checks whether the predicate is not nil for one element combination")
           (source-kind . "AutoLISP")
           (alphabetic-group . "V")
           (feature-groups . ("List Manipulation"))
           (supported-platforms . "Windows and Mac OS")
           (signature . "(vl-some predicate-function lst [lst ...])")
           (arguments . (("predicate-function" . "Type: Subroutine or Symbol\nThe test function. This can be any function that accepts as many arguments as there are lists provided with vl-some, and returns T on a user-specified condition. The predicate-function value can take one of the following forms:\n- A symbol (function name)\n- '(LAMBDA (A1 A2) ...)\n- (FUNCTION (LAMBDA (A1 A2) ...))")
                           ("lst" . "Type: List\nA list to be tested.")))
           (return-values . "Type: List or nil\nThe predicate value, if predicate-function returned a value other than nil; otherwise nil.")
           (release-information . nil)
           (history . nil)
           (examples . "The following example checks whether nlst (a number list) has equal elements in sequence:\n\n(setq nlst (list 0 2 pi pi 4))\n(0 2 3.14159 3.14159 4)\n\n(vl-some '= nlst (cdr nlst))\nT")
           (url . "https://help.autodesk.com/cloudhelp/2023/ENU/AutoCAD-AutoLISP-Reference/files/GUID-2840F793-DA88-4140-8A9D-EBAC47B62F9D.htm")
           (guid . "GUID-2840F793-DA88-4140-8A9D-EBAC47B62F9D"))))
    *autolisp-reference-parts*))

(setq *autolisp-reference-entry* nil)

(setq *autolisp-reference-value* "GUID-F3B27BD2-27FA-4185-B22C-85509175C171")

(setq *autolisp-reference-entry* (cons (cons 'guid *autolisp-reference-value*) *autolisp-reference-entry*))

(setq *autolisp-reference-value* "https://help.autodesk.com/cloudhelp/2023/ENU/AutoCAD-AutoLISP-Reference/files/GUID-F3B27BD2-27FA-4185-B22C-85509175C171.htm")

(setq *autolisp-reference-entry* (cons (cons 'url *autolisp-reference-value*) *autolisp-reference-entry*))

(setq *autolisp-reference-value* "Sort a list of numbers:\n\n(vl-sort '(3 2 1 3) '<)\n(1 2 3)\n\nNote that the result list contains only one 3.\n\nSort a list of 2D points by Y coordinate:\n\n(vl-sort '((1 3) (2 2) (3 1))\n             (function (lambda (e1 e2)\n                         (< (cadr e1) (cadr e2)))))\n((3 1) (2 2) (1 3))\n\nSort a list of symbols:\n\n(vl-sort\n   '(a d c b a)\n   '(lambda (s1 s2)\n    (< (vl-symbol-name s1) (vl-symbol-name s2))))\n(A B C D)       ;  Note that only one A remains in the result list")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nA list containing the elements of lst in the order specified by comparison-function. Duplicate elements may be eliminated from the list.")

(setq *autolisp-reference-entry* (cons (cons 'return-values *autolisp-reference-value*) *autolisp-reference-entry*))

(setq *autolisp-reference-value* nil)

(setq *autolisp-reference-string* "Type: Subroutine or Symbol\nA comparison function. This can be any function that accepts two arguments and returns T (or any non-nil value) if the first argument precedes the second in the sort order. The comparison-function value can take one of the following forms:\n- A symbol (function name)\n- '(LAMBDA (A1 A2) ...)\n- (FUNCTION (LAMBDA (A1 A2) ...))")

(setq *autolisp-reference-value* (cons (cons "comparison-function" *autolisp-reference-string*) *autolisp-reference-value*))

(setq *autolisp-reference-string* "Type: List\nAny list to sort.")

(setq *autolisp-reference-value* (cons (cons "lst" *autolisp-reference-string*) *autolisp-reference-value*))

(setq *autolisp-reference-entry* (cons (cons 'arguments *autolisp-reference-value*) *autolisp-reference-entry*))

(setq *autolisp-reference-value* "(vl-sort lst comparison-function)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("List Manipulation"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Sorts the elements in a list according to a given compare function")

(setq *autolisp-reference-entry* (cons (cons 'summary *autolisp-reference-value*) *autolisp-reference-entry*))

(setq *autolisp-reference-value* "vl-sort (AutoLISP)")

(setq *autolisp-reference-entry* (cons (cons 'title *autolisp-reference-value*) *autolisp-reference-entry*))

(setq *autolisp-reference-value* "vl-sort")

(setq *autolisp-reference-entry* (cons (cons 'name *autolisp-reference-value*) *autolisp-reference-entry*))

(setq *autolisp-reference-parts* (cons (list (cons "vl-sort" *autolisp-reference-entry*)) *autolisp-reference-parts*))

(setq *autolisp-reference-entry* nil)

(setq *autolisp-reference-value* "GUID-B21C91DD-D359-4370-84ED-317F8BBAF414")

(setq *autolisp-reference-entry* (cons (cons 'guid *autolisp-reference-value*) *autolisp-reference-entry*))

(setq *autolisp-reference-value* "https://help.autodesk.com/cloudhelp/2023/ENU/AutoCAD-AutoLISP-Reference/files/GUID-B21C91DD-D359-4370-84ED-317F8BBAF414.htm")

(setq *autolisp-reference-entry* (cons (cons 'url *autolisp-reference-value*) *autolisp-reference-entry*))

(setq *autolisp-reference-value* "Sort a list of characters in descending order:\n\n(vl-sort-i '(\"a\" \"d\" \"f\" \"c\") '>)\n(2 1 3 0)\n\nThe sorted list order is “f” “d” “c” “a”; “f” is the 3rd element (index 2) in the original list, “d” is the 2nd element (index 1) in the list, and so on.\n\nSort a list of numbers in ascending order:\n\n(vl-sort-i '(3 2 1 3) '<)\n(2 1 3 0)\n\nNote that both occurrences of 3 are accounted for in the result list.\n\nSort a list of 2D points by Y coordinate:\n\n(vl-sort-i '((1 3) (2 2) (3 1))\n         (function (lambda (e1 e2)\n                (< (cadr e1) (cadr e2)))))\n(2 1 0)\n\nSort a list of symbols:\n\n(vl-sort-i\n   '(a d c b a)\n   '(lambda (s1 s2)\n    (< (vl-symbol-name s1) (vl-symbol-name s2))))\n(4 0 3 2 1)\n\nNote that both a's are accounted for in the result list.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nA list containing the index values of the elements of lst, sorted in the order specified by comparison-function. Duplicate elements will be retained in the result.")

(setq *autolisp-reference-entry* (cons (cons 'return-values *autolisp-reference-value*) *autolisp-reference-entry*))

(setq *autolisp-reference-value* nil)

(setq *autolisp-reference-string* "Type: Subroutine or Symbol\nA comparison function. This can be any function that accepts two arguments and returns T (or any non-nil value) if the first argument precedes the second in the sort order. The comparison-function value can take one of the following forms:\n- A symbol (function name)\n- '(LAMBDA (A1 A2) ...)\n- (FUNCTION (LAMBDA (A1 A2) ...))")

(setq *autolisp-reference-value* (cons (cons "comparison-function" *autolisp-reference-string*) *autolisp-reference-value*))

(setq *autolisp-reference-string* "Type: List\nAny list to sort.")

(setq *autolisp-reference-value* (cons (cons "lst" *autolisp-reference-string*) *autolisp-reference-value*))

(setq *autolisp-reference-entry* (cons (cons 'arguments *autolisp-reference-value*) *autolisp-reference-entry*))

(setq *autolisp-reference-value* "(vl-sort-i lst comparison-function)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("List Manipulation"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Sorts the elements in a list according to a given compare function, and returns the element index numbers")

(setq *autolisp-reference-entry* (cons (cons 'summary *autolisp-reference-value*) *autolisp-reference-entry*))

(setq *autolisp-reference-value* "vl-sort-i (AutoLISP)")

(setq *autolisp-reference-entry* (cons (cons 'title *autolisp-reference-value*) *autolisp-reference-entry*))

(setq *autolisp-reference-value* "vl-sort-i")

(setq *autolisp-reference-entry* (cons (cons 'name *autolisp-reference-value*) *autolisp-reference-entry*))

(setq *autolisp-reference-parts* (cons (list (cons "vl-sort-i" *autolisp-reference-entry*)) *autolisp-reference-parts*))

(setq *autolisp-reference-entry* nil)

(setq *autolisp-reference-value* "GUID-3C1B15F7-CF97-4783-A725-231C3A1ABB11")

(setq *autolisp-reference-entry* (cons (cons 'guid *autolisp-reference-value*) *autolisp-reference-entry*))

(setq *autolisp-reference-value* "https://help.autodesk.com/cloudhelp/2023/ENU/AutoCAD-AutoLISP-Reference/files/GUID-3C1B15F7-CF97-4783-A725-231C3A1ABB11.htm")

(setq *autolisp-reference-entry* (cons (cons 'url *autolisp-reference-value*) *autolisp-reference-entry*))

(setq *autolisp-reference-value* "(vl-string->list \"\")\nnil\n\n(vl-string->list \"12\")\n(49 50)")

(setq *autolisp-reference-entry* (cons (cons 'examples *autolisp-reference-value*) *autolisp-reference-entry*))

(setq *autolisp-reference-value* "AutoCAD 2021\n- str\n- argument previously accepted an ASCII text string or character, but now accepts a Unicode text string or character.\n- Return value was modified to support Unicode characters and might be different than earlier releases. For example,\n- (vl-string->list \"1€\")\n- previously returned (49 128), but now returns (49 8364).\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: List or nil\nA list, each element of which is an integer representing the character codes of the corresponding characters in str.")

(setq *autolisp-reference-entry* (cons (cons 'return-values *autolisp-reference-value*) *autolisp-reference-entry*))

(setq *autolisp-reference-value* nil)

(setq *autolisp-reference-string* "Type: String\nA textual value.")

(setq *autolisp-reference-value* (cons (cons "str" *autolisp-reference-string*) *autolisp-reference-value*))

(setq *autolisp-reference-entry* (cons (cons 'arguments *autolisp-reference-value*) *autolisp-reference-entry*))

(setq *autolisp-reference-value* "(vl-string->list str)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("List Manipulation" "String-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Converts a string into a list of character codes")

(setq *autolisp-reference-entry* (cons (cons 'summary *autolisp-reference-value*) *autolisp-reference-entry*))

(setq *autolisp-reference-value* "vl-string->list (AutoLISP)")

(setq *autolisp-reference-entry* (cons (cons 'title *autolisp-reference-value*) *autolisp-reference-entry*))

(setq *autolisp-reference-value* "vl-string->list")

(setq *autolisp-reference-entry* (cons (cons 'name *autolisp-reference-value*) *autolisp-reference-entry*))

(setq *autolisp-reference-parts* (cons (list (cons "vl-string->list" *autolisp-reference-entry*)) *autolisp-reference-parts*))

(setq *autolisp-reference-entry* nil)

(setq *autolisp-reference-value* "GUID-5A68B31E-1EA7-434A-93FF-C05D9514A55B")

(setq *autolisp-reference-entry* (cons (cons 'guid *autolisp-reference-value*) *autolisp-reference-entry*))

(setq *autolisp-reference-value* "https://help.autodesk.com/cloudhelp/2023/ENU/AutoCAD-AutoLISP-Reference/files/GUID-5A68B31E-1EA7-434A-93FF-C05D9514A55B.htm")

(setq *autolisp-reference-entry* (cons (cons 'url *autolisp-reference-value*) *autolisp-reference-entry*))

(setq *autolisp-reference-value* "(vl-string-elt \"May the Force be with you\" 8)\n70")

(setq *autolisp-reference-entry* (cons (cons 'examples *autolisp-reference-value*) *autolisp-reference-entry*))

(setq *autolisp-reference-value* "AutoCAD 2021\n- str\n- argument previously accepted an ASCII text string or character (range of 1-255), but now accepts a Unicode text string or character (range of 1-65536).\n- Return value was modified to support Unicode characters and might be different than earlier releases. For example,\n- (vl-string-elt \"abc中\" 3)\n- previously returned 128, but now returns 20013.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: Integer or error\nA numeric value denoting the character code for the character at the specified position.\nNote: An error occurs if position is outside the range of the str.")

(setq *autolisp-reference-entry* (cons (cons 'return-values *autolisp-reference-value*) *autolisp-reference-entry*))

(setq *autolisp-reference-value* nil)

(setq *autolisp-reference-string* "Type: Integer\nA displacement in the string; the first character is displacement 0.")

(setq *autolisp-reference-value* (cons (cons "position" *autolisp-reference-string*) *autolisp-reference-value*))

(setq *autolisp-reference-string* "Type: String\nA textual value to be inspected.")

(setq *autolisp-reference-value* (cons (cons "str" *autolisp-reference-string*) *autolisp-reference-value*))

(setq *autolisp-reference-entry* (cons (cons 'arguments *autolisp-reference-value*) *autolisp-reference-entry*))

(setq *autolisp-reference-value* "(vl-string-elt str position)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns the character code for the character at a specified position in a string")

(setq *autolisp-reference-entry* (cons (cons 'summary *autolisp-reference-value*) *autolisp-reference-entry*))

(setq *autolisp-reference-value* "vl-string-elt (AutoLISP)")

(setq *autolisp-reference-entry* (cons (cons 'title *autolisp-reference-value*) *autolisp-reference-entry*))

(setq *autolisp-reference-value* "vl-string-elt")

(setq *autolisp-reference-entry* (cons (cons 'name *autolisp-reference-value*) *autolisp-reference-entry*))

(setq *autolisp-reference-parts* (cons (list (cons "vl-string-elt" *autolisp-reference-entry*)) *autolisp-reference-parts*))

(setq *autolisp-reference-parts*
  (cons
    '(("vl-string-left-trim" .
          ((name . "vl-string-left-trim")
           (title . "vl-string-left-trim (AutoLISP)")
           (summary . "Removes the specified characters from the beginning of a string")
           (source-kind . "AutoLISP")
           (alphabetic-group . "V")
           (feature-groups . ("String-Handling"))
           (supported-platforms . "Windows and Mac OS")
           (signature . "(vl-string-left-trim char-set str)")
           (arguments . (("char-set" . "Type: String\nA textual value listing the characters to be removed.")
                           ("str" . "Type: String\nThe textual value to be stripped of char-set.")))
           (return-values . "Type: String\nA textual value containing a substring of str with all leading characters in char-set removed.")
           (release-information . "Releases:\n- AutoCAD R14 and later on Windows\n- AutoCAD 2011 and later on Mac OS")
           (history . nil)
           (examples . "(vl-string-left-trim \" \\t\\n\" \"\\n\\t STR \")\n\"STR \"\n\n(vl-string-left-trim \"12456789\" \"12463CPO is not R2D2\")\n\"3CPO is not R2D2\"\n\n(vl-string-left-trim \" \" \"     There are too many spaces here\")\n\"There are too many spaces here\"")
           (url . "https://help.autodesk.com/cloudhelp/2023/ENU/AutoCAD-AutoLISP-Reference/files/GUID-24CB6E8B-9F4F-46DD-AB28-6481B86BA82A.htm")
           (guid . "GUID-24CB6E8B-9F4F-46DD-AB28-6481B86BA82A"))))
    *autolisp-reference-parts*))

(setq *autolisp-reference-entry* nil)

(setq *autolisp-reference-value* "GUID-D1EA6F47-146E-44BC-BBCA-40B7A874C0B8")

(setq *autolisp-reference-entry* (cons (cons 'guid *autolisp-reference-value*) *autolisp-reference-entry*))

(setq *autolisp-reference-value* "https://help.autodesk.com/cloudhelp/2023/ENU/AutoCAD-AutoLISP-Reference/files/GUID-D1EA6F47-146E-44BC-BBCA-40B7A874C0B8.htm")

(setq *autolisp-reference-entry* (cons (cons 'url *autolisp-reference-value*) *autolisp-reference-entry*))

(setq *autolisp-reference-value* "(vl-string-mismatch \"VL-FUN\" \"VL-VAR\")\n3\n\n(vl-string-mismatch \"vl-fun\" \"avl-var\")\n0\n\n(vl-string-mismatch \"abc中abc\" \"abc中ñ\")\n4\n\n(vl-string-mismatch \"€abc\" \"abc€\")\n0\n\n(vl-string-mismatch \"vl-fun\" \"avl-var\" 0 1)\n3\n\n(vl-string-mismatch \"VL-FUN\" \"Vl-vAR\")\n1\n\n(vl-string-mismatch \"VL-FUN\" \"Vl-vAR\" 0 0 T)\n3\n\n(vl-string-mismatch \"abc€\" \"ABC€\" 0 0 T)\n4")

(setq *autolisp-reference-entry* (cons (cons 'examples *autolisp-reference-value*) *autolisp-reference-entry*))

(setq *autolisp-reference-value* "AutoCAD 2021\n- str1\n- and\n- str2\n- arguments previously accepted ASCII text strings or characters, but these arguments now accept Unicode text strings or characters.\n- Return value was modified to support Unicode characters and might be different than earlier releases. In earlier releases, the length of a Unicode character was improperly calculated. For example,\n- (vl-string-mismatch \"abc中abc\" \"abc中ñ\")\n- previously returned 10, but now returns 4.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: Integer\nA numeric value.")

(setq *autolisp-reference-entry* (cons (cons 'return-values *autolisp-reference-value*) *autolisp-reference-entry*))

(setq *autolisp-reference-value* nil)

(setq *autolisp-reference-string* "Type: T or nil\nIf T is specified for this argument, case is ignored; otherwise, case is considered.")

(setq *autolisp-reference-value* (cons (cons "ignore-case-p" *autolisp-reference-string*) *autolisp-reference-value*))

(setq *autolisp-reference-string* "Type: Integer\nA numeric value identifying the position to search from in the second string; 0 if omitted.")

(setq *autolisp-reference-value* (cons (cons "pos2" *autolisp-reference-string*) *autolisp-reference-value*))

(setq *autolisp-reference-string* "Type: Integer\nA numeric value identifying the position to search from in the first string; 0 if omitted.")

(setq *autolisp-reference-value* (cons (cons "pos1" *autolisp-reference-string*) *autolisp-reference-value*))

(setq *autolisp-reference-string* "Type: String\nThe second textual value to be matched.")

(setq *autolisp-reference-value* (cons (cons "str2" *autolisp-reference-string*) *autolisp-reference-value*))

(setq *autolisp-reference-string* "Type: String\nThe first textual value to be matched.")

(setq *autolisp-reference-value* (cons (cons "str1" *autolisp-reference-string*) *autolisp-reference-value*))

(setq *autolisp-reference-entry* (cons (cons 'arguments *autolisp-reference-value*) *autolisp-reference-entry*))

(setq *autolisp-reference-value* "(vl-string-mismatch str1 str2 [pos1 pos2 ignore-case-p])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns the length of the longest common prefix for two strings, starting at specified positions")

(setq *autolisp-reference-entry* (cons (cons 'summary *autolisp-reference-value*) *autolisp-reference-entry*))

(setq *autolisp-reference-value* "vl-string-mismatch (AutoLISP)")

(setq *autolisp-reference-entry* (cons (cons 'title *autolisp-reference-value*) *autolisp-reference-entry*))

(setq *autolisp-reference-value* "vl-string-mismatch")

(setq *autolisp-reference-entry* (cons (cons 'name *autolisp-reference-value*) *autolisp-reference-entry*))

(setq *autolisp-reference-parts* (cons (list (cons "vl-string-mismatch" *autolisp-reference-entry*)) *autolisp-reference-parts*))

(setq *autolisp-reference-entry* nil)

(setq *autolisp-reference-value* "GUID-2B0BF48B-FA26-431B-8EC3-DD0BD9F147A0")

(setq *autolisp-reference-entry* (cons (cons 'guid *autolisp-reference-value*) *autolisp-reference-entry*))

(setq *autolisp-reference-value* "https://help.autodesk.com/cloudhelp/2023/ENU/AutoCAD-AutoLISP-Reference/files/GUID-2B0BF48B-FA26-431B-8EC3-DD0BD9F147A0.htm")

(setq *autolisp-reference-entry* (cons (cons 'url *autolisp-reference-value*) *autolisp-reference-entry*))

(setq *autolisp-reference-value* "(vl-string-position (ascii \"z\") \"azbdc\")\n1\n\n(vl-string-position 122 \"azbzc\")\n1\n\n(vl-string-position (ascii \"x\") \"azbzc\")\nnil\n\nThe search string used in the following example contains two \"z\" characters. Reading from left to right, with the first character being displacement 0, there is one z at displacement 1 and another z at displacement 3:\n\n(vl-string-position (ascii \"z\") \"azbzlmnqc\")\n1\n\nSearching from left to right (the default), the \"z\" in position 1 is the first one vl-string-position encounters. But when searching from right to left, as in the following example, the \"z\" in position 3 is the first one encountered:\n\n(vl-string-position (ascii \"z\") \"azbzlmnqc\" nil T)\n3")

(setq *autolisp-reference-entry* (cons (cons 'examples *autolisp-reference-value*) *autolisp-reference-entry*))

(setq *autolisp-reference-value* "AutoCAD 2021\n- char-code\n- argument previously accepted an ASCII character code, but now accepts a Unicode character code.\n- str\n- argument previously accepted an ASCII text string or character, but now accepts a Unicode text string or character.\n- Return value was modified to support Unicode characters and might be different than earlier releases. In earlier releases, the length of a Unicode character was improperly calculated. For example,\n- (vl-string-position (ascii \"€\") \"中€\" 0)\n- previously returned 7, but now returns 1.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: Integer or nil\nAn integer representing the displacement at which char-code was found from the beginning of the string; nil if the character was not found.")

(setq *autolisp-reference-entry* (cons (cons 'return-values *autolisp-reference-value*) *autolisp-reference-entry*))

(setq *autolisp-reference-value* nil)

(setq *autolisp-reference-string* "Type: T or nil\nIf T is specified for this argument, the search begins at the end of the string and continues backward to pos.")

(setq *autolisp-reference-value* (cons (cons "from-end-p" *autolisp-reference-string*) *autolisp-reference-value*))

(setq *autolisp-reference-string* "Type: Integer\nThe position to begin searching from in the string (first character is 0); 0 if omitted.")

(setq *autolisp-reference-value* (cons (cons "start-pos" *autolisp-reference-string*) *autolisp-reference-value*))

(setq *autolisp-reference-string* "Type: String\nThe textual value to be searched.")

(setq *autolisp-reference-value* (cons (cons "str" *autolisp-reference-string*) *autolisp-reference-value*))

(setq *autolisp-reference-string* "Type: Integer\nA numeric value representation of the character to be searched.")

(setq *autolisp-reference-value* (cons (cons "char-code" *autolisp-reference-string*) *autolisp-reference-value*))

(setq *autolisp-reference-entry* (cons (cons 'arguments *autolisp-reference-value*) *autolisp-reference-entry*))

(setq *autolisp-reference-value* "(vl-string-position char-code str [start-pos [from-end-p]])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Looks for a character with the specified character code in a string")

(setq *autolisp-reference-entry* (cons (cons 'summary *autolisp-reference-value*) *autolisp-reference-entry*))

(setq *autolisp-reference-value* "vl-string-position (AutoLISP)")

(setq *autolisp-reference-entry* (cons (cons 'title *autolisp-reference-value*) *autolisp-reference-entry*))

(setq *autolisp-reference-value* "vl-string-position")

(setq *autolisp-reference-entry* (cons (cons 'name *autolisp-reference-value*) *autolisp-reference-entry*))

(setq *autolisp-reference-parts* (cons (list (cons "vl-string-position" *autolisp-reference-entry*)) *autolisp-reference-parts*))

(setq *autolisp-reference-parts*
  (cons
    '(("vl-string-right-trim" .
          ((name . "vl-string-right-trim")
           (title . "vl-string-right-trim (AutoLISP)")
           (summary . "Removes the specified characters from the end of a string")
           (source-kind . "AutoLISP")
           (alphabetic-group . "V")
           (feature-groups . ("String-Handling"))
           (supported-platforms . "Windows and Mac OS")
           (signature . "(vl-string-right-trim char-set str)")
           (arguments . (("char-set" . "Type: String\nA textual value listing the characters to be removed.")
                           ("str" . "Type: String\nThe textual value to be stripped of char-set.")))
           (return-values . "Type: String\nA textual value containing a substring of str with all trailing characters in char-set removed.")
           (release-information . "Releases:\n- AutoCAD R14 and later on Windows\n- AutoCAD 2011 and later on Mac OS")
           (history . nil)
           (examples . "(vl-string-right-trim \" \\t\\n\" \" STR \\n\\t \")\n\" STR\"\n\n(vl-string-right-trim \"1356789\" \"3CPO is not R2D267891\")\n\"3CPO is not R2D2\"\n\n(vl-string-right-trim \" \" \"There are too many spaces here      \")\n\"There are too many spaces here\"")
           (url . "https://help.autodesk.com/cloudhelp/2023/ENU/AutoCAD-AutoLISP-Reference/files/GUID-532CDF83-7A7F-4B54-8362-F5B7FB35C220.htm")
           (guid . "GUID-532CDF83-7A7F-4B54-8362-F5B7FB35C220"))))
    *autolisp-reference-parts*))

(setq *autolisp-reference-entry* nil)

(setq *autolisp-reference-value* "GUID-4E7AE1DA-1ED5-4D96-A7D3-34241AA94AA6")

(setq *autolisp-reference-entry* (cons (cons 'guid *autolisp-reference-value*) *autolisp-reference-entry*))

(setq *autolisp-reference-value* "https://help.autodesk.com/cloudhelp/2023/ENU/AutoCAD-AutoLISP-Reference/files/GUID-4E7AE1DA-1ED5-4D96-A7D3-34241AA94AA6.htm")

(setq *autolisp-reference-entry* (cons (cons 'url *autolisp-reference-value*) *autolisp-reference-entry*))

(setq *autolisp-reference-value* "(vl-string-search \"foo\" \"pfooyey on you\")\n1\n\n(vl-string-search \"who\" \"pfooyey on you\")\nnil\n\n(vl-string-search \"foo\" \"fooey-more-fooey\" 1)\n11\n\n(vl-string-search \"€\" \"€abc中€\")\n0\n\n(vl-string-search \"测试\" \"€abc中€\" 1)\nnil\n\n(vl-string-search \"€\" \"€abc中€\" 1)\n5")

(setq *autolisp-reference-entry* (cons (cons 'examples *autolisp-reference-value*) *autolisp-reference-entry*))

(setq *autolisp-reference-value* "AutoCAD 2021\n- pattern\n- and\n- str\n- arguments previously accepted ASCII text strings or characters, but they now accept Unicode text strings or characters.\n- Return value was modified to support Unicode characters and might be different than earlier releases. In earlier releases, the length of a Unicode character was improperly calculated. For example,\n- (vl-string-search \"€\" \"€abc中€\" 1)\n- previously returned 11, but now returns 5.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: Integer\nA numeric value representing the position in the string where the specified pattern was found; otherwise nil if the pattern is not found; the first character of the string is position 0.")

(setq *autolisp-reference-entry* (cons (cons 'return-values *autolisp-reference-value*) *autolisp-reference-entry*))

(setq *autolisp-reference-value* nil)

(setq *autolisp-reference-string* "Type: Integer\nA numeric value identifying the starting position of the search; 0 if omitted.")

(setq *autolisp-reference-value* (cons (cons "start-pos" *autolisp-reference-string*) *autolisp-reference-value*))

(setq *autolisp-reference-string* "Type: String\nThe textual value to be searched for pattern.")

(setq *autolisp-reference-value* (cons (cons "str" *autolisp-reference-string*) *autolisp-reference-value*))

(setq *autolisp-reference-string* "Type: String\nThe textual value containing the pattern to be searched for.")

(setq *autolisp-reference-value* (cons (cons "pattern" *autolisp-reference-string*) *autolisp-reference-value*))

(setq *autolisp-reference-entry* (cons (cons 'arguments *autolisp-reference-value*) *autolisp-reference-entry*))

(setq *autolisp-reference-value* "(vl-string-search pattern str [start-pos])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Searches for the specified pattern in a string")

(setq *autolisp-reference-entry* (cons (cons 'summary *autolisp-reference-value*) *autolisp-reference-entry*))

(setq *autolisp-reference-value* "vl-string-search (AutoLISP)")

(setq *autolisp-reference-entry* (cons (cons 'title *autolisp-reference-value*) *autolisp-reference-entry*))

(setq *autolisp-reference-value* "vl-string-search")

(setq *autolisp-reference-entry* (cons (cons 'name *autolisp-reference-value*) *autolisp-reference-entry*))

(setq *autolisp-reference-parts* (cons (list (cons "vl-string-search" *autolisp-reference-entry*)) *autolisp-reference-parts*))

(setq *autolisp-reference-entry* nil)

(setq *autolisp-reference-value* "GUID-D8EE91DC-D4DB-43E0-9AFE-5FA166C0896D")

(setq *autolisp-reference-entry* (cons (cons 'guid *autolisp-reference-value*) *autolisp-reference-entry*))

(setq *autolisp-reference-value* "https://help.autodesk.com/cloudhelp/2023/ENU/AutoCAD-AutoLISP-Reference/files/GUID-D8EE91DC-D4DB-43E0-9AFE-5FA166C0896D.htm")

(setq *autolisp-reference-entry* (cons (cons 'url *autolisp-reference-value*) *autolisp-reference-entry*))

(setq *autolisp-reference-value* "Replace the string \"Ben\" with \"Obi-wan\":\n\n(vl-string-subst \"Obi-wan\" \"Ben\" \"Ben Kenobi\")\n\"Obi-wan Kenobi\"\n\nReplace \"Ben\" with \"Obi-wan\":\n\n(vl-string-subst \"Obi-wan\" \"Ben\" \"ben Kenobi\")\n\"ben Kenobi\"\n\nNothing was substituted because vl-string-subst did not find a match for \"Ben\"; the \"ben\" in the string that was searched begins with a lowercase \"b\".\n\nReplace \"Ben\" with \"Obi-wan\":\n\n(vl-string-subst \"Obi-wan\" \"Ben\" \"Ben Kenobi Ben\")\n\"Obi-wan Kenobi Ben\"\n\nNote that there are two occurrences of \"Ben\" in the string that was searched, but vl-string-subst replaces only the first occurrence.\n\nReplace \"Ben\" with \"Obi-wan,\" but start the search at the fourth character in the string:\n\n(vl-string-subst \"Obi-wan\" \"Ben\" \"Ben \\\"Ben\\\" Kenobi\" 3)\n\"Ben \\\"Obi-wan\\\" Kenobi\"\n\nThere are two occurrences of \"Ben\" in the stri")

(setq *autolisp-reference-value* (strcat *autolisp-reference-value* "ng that was searched, but because vl-string-subst was instructed to begin searching at the fourth character, it found and replaced the second occurrence, not the first."))

(setq *autolisp-reference-entry* (cons (cons 'examples *autolisp-reference-value*) *autolisp-reference-entry*))

(setq *autolisp-reference-value* "AutoCAD 2021\n- new-str\n- ,\n- pattern\n- and\n- str\n- arguments previously accepted ASCII text strings or characters, but now accept Unicode text strings or characters.\n- Return value was modified to support Unicode characters and might be different than earlier releases. In earlier releases, the length of a Unicode character was improperly calculated. For example,\n- (vl-string-subst \"中\" \"€\" \"abc中€bec\" 5)\n- previously returned \"abc中中bec\", but now returns \"abc中€bec\".\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: String\nThe value of str after any substitutions have been made.")

(setq *autolisp-reference-entry* (cons (cons 'return-values *autolisp-reference-value*) *autolisp-reference-entry*))

(setq *autolisp-reference-value* nil)

(setq *autolisp-reference-string* "Type: Integer\nA numeric value identifying the starting position of the search; 0 if omitted.")

(setq *autolisp-reference-value* (cons (cons "start-pos" *autolisp-reference-string*) *autolisp-reference-value*))

(setq *autolisp-reference-string* "Type: String\nThe textual value to be searched for pattern.")

(setq *autolisp-reference-value* (cons (cons "str" *autolisp-reference-string*) *autolisp-reference-value*))

(setq *autolisp-reference-string* "Type: String\nThe textual value containing the pattern to be replaced.")

(setq *autolisp-reference-value* (cons (cons "pattern" *autolisp-reference-string*) *autolisp-reference-value*))

(setq *autolisp-reference-string* "Type: String\nThe textual value to be substituted for pattern.")

(setq *autolisp-reference-value* (cons (cons "new-str" *autolisp-reference-string*) *autolisp-reference-value*))

(setq *autolisp-reference-entry* (cons (cons 'arguments *autolisp-reference-value*) *autolisp-reference-entry*))

(setq *autolisp-reference-value* "(vl-string-subst new-str pattern str [start-pos])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Substitutes one string for another, within a string")

(setq *autolisp-reference-entry* (cons (cons 'summary *autolisp-reference-value*) *autolisp-reference-entry*))

(setq *autolisp-reference-value* "vl-string-subst (AutoLISP)")

(setq *autolisp-reference-entry* (cons (cons 'title *autolisp-reference-value*) *autolisp-reference-entry*))

(setq *autolisp-reference-value* "vl-string-subst")

(setq *autolisp-reference-entry* (cons (cons 'name *autolisp-reference-value*) *autolisp-reference-entry*))

(setq *autolisp-reference-parts* (cons (list (cons "vl-string-subst" *autolisp-reference-entry*)) *autolisp-reference-parts*))

(setq *autolisp-reference-entry* nil)

(setq *autolisp-reference-value* "GUID-57060085-C79D-4613-B438-506AC443BCE7")

(setq *autolisp-reference-entry* (cons (cons 'guid *autolisp-reference-value*) *autolisp-reference-entry*))

(setq *autolisp-reference-value* "https://help.autodesk.com/cloudhelp/2023/ENU/AutoCAD-AutoLISP-Reference/files/GUID-57060085-C79D-4613-B438-506AC443BCE7.htm")

(setq *autolisp-reference-entry* (cons (cons 'url *autolisp-reference-value*) *autolisp-reference-entry*))

(setq *autolisp-reference-value* "(vl-string-translate \"abcABC\" \"123123\" \"A is a, B is b, C is c\")\n\"1 is 1, 2 is 2, 3 is 3\"\n\n(vl-string-translate \"abc\" \"123\" \"A is a, B is b, C is c\")\n\"A is 1, B is 2, C is 3\"")

(setq *autolisp-reference-entry* (cons (cons 'examples *autolisp-reference-value*) *autolisp-reference-entry*))

(setq *autolisp-reference-value* "AutoCAD 2021\n- source-set\n- ,\n- dest-set\n- and\n- str\n- arguments previously accepted ASCII text strings or characters, but they now accept Unicode text strings or characters.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows\n- AutoCAD 2011 and later on Mac OS")

(setq *autolisp-reference-entry* (cons (cons 'release-information *autolisp-reference-value*) *autolisp-reference-entry*))

(setq *autolisp-reference-value* "Type: String\nThe value of str after any substitutions have been made.")

(setq *autolisp-reference-entry* (cons (cons 'return-values *autolisp-reference-value*) *autolisp-reference-entry*))

(setq *autolisp-reference-value* nil)

(setq *autolisp-reference-string* "Type: String\nThe textual value to be searched and translated.")

(setq *autolisp-reference-value* (cons (cons "str" *autolisp-reference-string*) *autolisp-reference-value*))

(setq *autolisp-reference-string* "Type: String\nCharacters to be substituted for those in source-set.")

(setq *autolisp-reference-value* (cons (cons "dest-set" *autolisp-reference-string*) *autolisp-reference-value*))

(setq *autolisp-reference-string* "Type: String\nCharacters to be matched.")

(setq *autolisp-reference-value* (cons (cons "source-set" *autolisp-reference-string*) *autolisp-reference-value*))

(setq *autolisp-reference-entry* (cons (cons 'arguments *autolisp-reference-value*) *autolisp-reference-entry*))

(setq *autolisp-reference-value* "(vl-string-translate source-set dest-set str)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Replaces characters in a string with a specified set of characters")

(setq *autolisp-reference-entry* (cons (cons 'summary *autolisp-reference-value*) *autolisp-reference-entry*))

(setq *autolisp-reference-value* "vl-string-translate (AutoLISP)")

(setq *autolisp-reference-entry* (cons (cons 'title *autolisp-reference-value*) *autolisp-reference-entry*))

(setq *autolisp-reference-value* "vl-string-translate")

(setq *autolisp-reference-entry* (cons (cons 'name *autolisp-reference-value*) *autolisp-reference-entry*))

(setq *autolisp-reference-parts* (cons (list (cons "vl-string-translate" *autolisp-reference-entry*)) *autolisp-reference-parts*))

(setq *autolisp-reference-parts*
  (cons
    '(("vl-string-trim" .
          ((name . "vl-string-trim")
           (title . "vl-string-trim (AutoLISP)")
           (summary . "Removes the specified characters from the beginning and end of a string")
           (source-kind . "AutoLISP")
           (alphabetic-group . "V")
           (feature-groups . ("String-Handling"))
           (supported-platforms . "Windows and Mac OS")
           (signature . "(vl-string-trim char-set str)")
           (arguments . (("char-set" . "Type: String\nCharacters to be removed.")
                           ("str" . "Type: String\nThe textual value to be trimmed of char-set.")))
           (return-values . "Type: String\nThe value of str, after any characters have been trimmed.")
           (release-information . "Releases:\n- AutoCAD R14 and later on Windows\n- AutoCAD 2011 and later on Mac OS")
           (history . nil)
           (examples . "(vl-string-trim \" \\t\\n\" \" \\t\\n STR \\n\\t \")\n\"STR\"\n\n(vl-string-trim \"this is junk\" \"this is junk Don't call this junk! this is junk\")\n\"Don't call this junk!\"\n\n(vl-string-trim \" \" \"      Leave me alone   \")\n\"Leave me alone\"")
           (url . "https://help.autodesk.com/cloudhelp/2023/ENU/AutoCAD-AutoLISP-Reference/files/GUID-FF1DA441-C9D8-4C99-BC6E-B2A72B562389.htm")
           (guid . "GUID-FF1DA441-C9D8-4C99-BC6E-B2A72B562389"))))
    *autolisp-reference-parts*))

(setq *autolisp-reference-parts*
  (cons
    '(("vl-symbol-name" .
          ((name . "vl-symbol-name")
           (title . "vl-symbol-name (AutoLISP)")
           (summary . "Returns a string containing the name of a symbol")
           (source-kind . "AutoLISP")
           (alphabetic-group . "V")
           (feature-groups . ("Symbol-Handling"))
           (supported-platforms . "Windows and Mac OS")
           (signature . "(vl-symbol-name symbol)")
           (arguments . (("symbol" . "Type: Symbol\nAny LISP symbol.")))
           (return-values . "Type: String or error\nA string containing the name of the supplied symbol argument, in uppercase.")
           (release-information . nil)
           (history . nil)
           (examples . "(vl-symbol-name 'S::STARTUP)\n\"S::STARTUP\"\n\n(progn (setq sym 'my-var) (vl-symbol-name sym))\n\"MY-VAR\"\n\n(vl-symbol-name 1)\n; *** ERROR: bad argument type: symbolp 1")
           (url . "https://help.autodesk.com/cloudhelp/2023/ENU/AutoCAD-AutoLISP-Reference/files/GUID-6F5B5B70-3C2D-4301-84BE-FDEEF0C32B30.htm")
           (guid . "GUID-6F5B5B70-3C2D-4301-84BE-FDEEF0C32B30"))))
    *autolisp-reference-parts*))

(setq *autolisp-reference-parts*
  (cons
    '(("vl-symbol-value" .
          ((name . "vl-symbol-value")
           (title . "vl-symbol-value (AutoLISP)")
           (summary . "Returns the current value bound to a symbol")
           (source-kind . "AutoLISP")
           (alphabetic-group . "V")
           (feature-groups . ("Symbol-Handling"))
           (supported-platforms . "Windows and Mac OS")
           (signature . "(vl-symbol-value symbol)")
           (arguments . (("symbol" . "Type: Symbol\nAny LISP symbol.")))
           (return-values . "Type: Integer, Real, String, List, File, Ename (entity name), T, or nil\nThe value of symbol, after evaluation.")
           (release-information . nil)
           (history . nil)
           (examples . "(vl-symbol-value 't)\nT\n\n(vl-symbol-value 'PI)\n3.14159\n\n(progn (setq sym 'PAUSE) (vl-symbol-value sym))\n\"\\\\\"")
           (url . "https://help.autodesk.com/cloudhelp/2023/ENU/AutoCAD-AutoLISP-Reference/files/GUID-5DAAABCF-7210-4A90-809D-6C27CCEF64F1.htm")
           (guid . "GUID-5DAAABCF-7210-4A90-809D-6C27CCEF64F1"))))
    *autolisp-reference-parts*))

(setq *autolisp-reference-parts*
  (cons
    '(("vl-symbolp" .
          ((name . "vl-symbolp")
           (title . "vl-symbolp (AutoLISP)")
           (summary . "Identifies whether or not a specified object is a symbol")
           (source-kind . "AutoLISP")
           (alphabetic-group . "V")
           (feature-groups . ("Symbol-Handling"))
           (supported-platforms . "Windows and Mac OS")
           (signature . "(vl-symbolp object)")
           (arguments . (("object" . "Type: Integer, Real, String, List, File, Symbol, Ename (entity name), T, or nil\nAny LISP object.")))
           (return-values . "Type: T or nil\nT if object is a symbol; otherwise nil.")
           (release-information . nil)
           (history . nil)
           (examples . "(vl-symbolp t)\nT\n\n(vl-symbolp nil)\nnil\n\n(vl-symbolp 1)\nnil\n\n(vl-symbolp (list 1))\nnil")
           (url . "https://help.autodesk.com/cloudhelp/2023/ENU/AutoCAD-AutoLISP-Reference/files/GUID-F51AFE0A-CA6C-428D-8E8D-3607BF551990.htm")
           (guid . "GUID-F51AFE0A-CA6C-428D-8E8D-3607BF551990"))))
    *autolisp-reference-parts*))

(setq *autolisp-reference-parts*
  (cons
    '(("vl-unload-vlx" .
          ((name . "vl-unload-vlx")
           (title . "vl-unload-vlx (AutoLISP)")
           (summary . "Unload a VLX application that is loaded in its own namespace")
           (source-kind . "AutoLISP")
           (alphabetic-group . "V")
           (feature-groups . ("VLX Namespace"))
           (supported-platforms . "Windows only")
           (signature . "(vl-unload-vlx appname)")
           (arguments . (("appname" . "Type: String\nName of a VLX application that is loaded in its own namespace. Do not include the .vlx extension.")))
           (return-values . "Type: T or error\nT if successful; otherwise vl-unload-vlx results in an error.")
           (release-information . nil)
           (history . nil)
           (examples . "Assuming that vlxns is an application that is loaded in its own namespace, the following command unloads vlxns:\n\n(vl-unload-vlx \"vlxns\")\nT\n\nTry unloading vlxns again:\n\n(vl-unload-vlx \"vlxns\")\n; *** ERROR: LISP Application is not found VLXNS\n\nThe vl-unload-vlx command fails this time, because the application was not loaded.")
           (url . "https://help.autodesk.com/cloudhelp/2023/ENU/AutoCAD-AutoLISP-Reference/files/GUID-7AF6AC48-3435-4625-B210-C8FFFF1D2717.htm")
           (guid . "GUID-7AF6AC48-3435-4625-B210-C8FFFF1D2717"))))
    *autolisp-reference-parts*))

(setq *autolisp-reference-entry* nil)

(setq *autolisp-reference-value* "GUID-54FD698E-8D94-4E27-9DF1-3F7E9D451E05")

(setq *autolisp-reference-entry* (cons (cons 'guid *autolisp-reference-value*) *autolisp-reference-entry*))

(setq *autolisp-reference-value* "https://help.autodesk.com/cloudhelp/2023/ENU/AutoCAD-AutoLISP-Reference/files/GUID-54FD698E-8D94-4E27-9DF1-3F7E9D451E05.htm")

(setq *autolisp-reference-entry* (cons (cons 'url *autolisp-reference-value*) *autolisp-reference-entry*))

(setq *autolisp-reference-value* "(vl-vbaload \"c:/program files/<AutoCAD installation directory>/sample/vba/drawline.dvb\")\n\"c:\\\\program files\\\\<AutoCAD installation directory>\\\\sample\\\\vba\\\\drawline.dvb\"")

(setq *autolisp-reference-entry* (cons (cons 'examples *autolisp-reference-value*) *autolisp-reference-entry*))

(setq *autolisp-reference-value* "AutoCAD 2021\n- filename\n- argument previously accepted an ASCII text string, but now accepts a Unicode text string.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R14 and later on Windows")

(setq *autolisp-reference-entry* (cons (cons 'release-information *autolisp-reference-value*) *autolisp-reference-entry*))

(setq *autolisp-reference-value* "Type: String or error\nA textual value containing the file name and path of the VBA project; otherwise an error occurs if the file is not found.\nImportant: Starting with AutoCAD 2014-based products, custom applications must work under secure mode; when the SECURELOAD system variable is set to 1 or 2. When operating under secure mode, the program is restricted to loading and executing files that contain code from trusted locations; trusted locations are specified by the TRUSTEDPATHS system variable.")

(setq *autolisp-reference-entry* (cons (cons 'return-values *autolisp-reference-value*) *autolisp-reference-entry*))

(setq *autolisp-reference-value* nil)

(setq *autolisp-reference-string* "Type: String\nName of the VBA project file to be loaded.")

(setq *autolisp-reference-value* (cons (cons "filename" *autolisp-reference-string*) *autolisp-reference-value*))

(setq *autolisp-reference-entry* (cons (cons 'arguments *autolisp-reference-value*) *autolisp-reference-entry*))

(setq *autolisp-reference-value* "(vl-vbaload filename)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Application-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Loads a VBA project")

(setq *autolisp-reference-entry* (cons (cons 'summary *autolisp-reference-value*) *autolisp-reference-entry*))

(setq *autolisp-reference-value* "vl-vbaload (AutoLISP)")

(setq *autolisp-reference-entry* (cons (cons 'title *autolisp-reference-value*) *autolisp-reference-entry*))

(setq *autolisp-reference-value* "vl-vbaload")

(setq *autolisp-reference-entry* (cons (cons 'name *autolisp-reference-value*) *autolisp-reference-entry*))

(setq *autolisp-reference-parts* (cons (list (cons "vl-vbaload" *autolisp-reference-entry*)) *autolisp-reference-parts*))

(setq *autolisp-reference-parts*
  (cons
    '(("vl-vbarun" .
          ((name . "vl-vbarun")
           (title . "vl-vbarun (AutoLISP)")
           (summary . "Runs a VBA macro")
           (source-kind . "AutoLISP")
           (alphabetic-group . "V")
           (feature-groups . ("Application-Handling"))
           (supported-platforms . "Windows only")
           (signature . "(vl-vbarun macroname)")
           (arguments . (("macroname" . "Type: String\nName of a macro in a loaded VBA project.")))
           (return-values . "Type: String or error\nThe value of the macroname argument; otherwise, an error occurs.")
           (release-information . "Releases:\n- AutoCAD R14 and later on Windows")
           (history . nil)
           (examples . "Load a VBA project file:\n\n(vl-vbaload \"c:/program files/<AutoCAD installation directory>/sample/vba/drawline.dvb\")\n\"c:\\\\program files\\\\<AutoCAD installation directory>\\\\sample\\\\vba\\\\drawline.dvb\"\n\nRun a macro from the loaded project:\n\n(vl-vbarun \"drawline\")\n\"drawline\"")
           (url . "https://help.autodesk.com/cloudhelp/2023/ENU/AutoCAD-AutoLISP-Reference/files/GUID-75387617-9144-49CB-97E4-03B4CD29973B.htm")
           (guid . "GUID-75387617-9144-49CB-97E4-03B4CD29973B"))))
    *autolisp-reference-parts*))

(setq *autolisp-reference-parts*
  (cons
    '(("vl-vlx-loaded-p" .
          ((name . "vl-vlx-loaded-p")
           (title . "vl-vlx-loaded-p (AutoLISP)")
           (summary . "Determines whether a separate-namespace VLX is currently loaded")
           (source-kind . "AutoLISP")
           (alphabetic-group . "V")
           (feature-groups . ("VLX Namespace"))
           (supported-platforms . "Windows only")
           (signature . "(vl-vlx-loaded-p appname)")
           (arguments . (("appname" . "Type: String\nName of a VLX application.")))
           (return-values . "Type: T or nil\nT if the application is loaded, nil if it is not loaded.")
           (release-information . nil)
           (history . nil)
           (examples . "Check to see if the vlxns application is loaded in its own namespace:\n\n(vl-vlx-loaded-p \"vlxns\")\nnil\n\nThe application is not loaded in its own namespace.\n\nNow load vlxns:\n\n(load \"vlxns.vlx\")\nnil\n\nCheck to see if the vlxns application loaded successfully:\n\n(vl-vlx-loaded-p \"vlxns\")\nT\n\nThis example assumes vlxns was defined to run in its own namespace. If the application was not defined to run in its own namespace, it would load into the current document's namespace and vl-vlx-loaded-p would return nil.")
           (url . "https://help.autodesk.com/cloudhelp/2023/ENU/AutoCAD-AutoLISP-Reference/files/GUID-2322688B-F1FA-416E-AEF0-E14256717588.htm")
           (guid . "GUID-2322688B-F1FA-416E-AEF0-E14256717588"))))
    *autolisp-reference-parts*))

(setq *autolisp-reference-parts*
  (cons
    '(("vlax-3D-point" .
          ((name . "vlax-3D-point")
           (title . "vlax-3D-point (AutoLISP/ActiveX)")
           (summary . "Creates ActiveX-compatible (variant) 3D point structure")
           (source-kind . "AutoLISP/ActiveX")
           (alphabetic-group . "V")
           (feature-groups . ("Data Conversion Functions Reference (AutoLISP/ActiveX)"))
           (supported-platforms . "Windows only")
           (signature . "(vlax-3D-point lst)\n\n(vlax-3D-point x y [z])")
           (arguments . (("lst" . "Type: List\nA list of two or three numbers, representing points.")
                           ("x, y" . "Type: Integer or Real\nNumbers representing X and Y coordinates of a point.")
                           ("z" . "Type: Integer or Real\nA number representing the Z coordinate of a point.")))
           (return-values . "Type: Variant\nA variant containing a three-element array of doubles.")
           (release-information . nil)
           (history . nil)
           (examples . "(vlax-3D-point 5 20)\n#<variant 8197 ...>\n\n(vlax-3D-point '(33.6 44.0 90.0))\n<variant 8197 ...>")
           (url . "https://help.autodesk.com/cloudhelp/2023/ENU/AutoCAD-AutoLISP-Reference/files/GUID-4C3B6017-BA57-451D-8CF8-C8539E9517F6.htm")
           (guid . "GUID-4C3B6017-BA57-451D-8CF8-C8539E9517F6"))))
    *autolisp-reference-parts*))

(setq *autolisp-reference-entry* nil)

(setq *autolisp-reference-value* "GUID-42392DA4-4A2B-4D34-AA7B-A5ACAF727E54")

(setq *autolisp-reference-entry* (cons (cons 'guid *autolisp-reference-value*) *autolisp-reference-entry*))

(setq *autolisp-reference-value* "https://help.autodesk.com/cloudhelp/2023/ENU/AutoCAD-AutoLISP-Reference/files/GUID-42392DA4-4A2B-4D34-AA7B-A5ACAF727E54.htm")

(setq *autolisp-reference-entry* (cons (cons 'url *autolisp-reference-value*) *autolisp-reference-entry*))

(setq *autolisp-reference-value* "The hello-autocad function in the following example has no c: prefix, but vlax-add-cmd makes it visible as an ObjectARX-style command at the AutoCAD Command prompt:\n\n(defun hello-autocad () (princ \"hello Visual LISP\"))\nHELLO-AUTOCAD\n\n(vlax-add-cmd \"hello-autocad\" 'hello-autocad)\n\"hello-autocad\"")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String or nil\nThe global-name argument, if successful. The function returns nil if acedRegCmds->addCommand(...) returns an error condition.")

(setq *autolisp-reference-entry* (cons (cons 'return-values *autolisp-reference-value*) *autolisp-reference-entry*))

(setq *autolisp-reference-value* nil)

(setq *autolisp-reference-string* "Type: Integer\nA numeric value (defaults to ACRX_CMD_MODAL + ACRX_CMD_REDRAW)\nThe primary flags are\nACRX_CMD_MODAL (0) -- Command cannot be invoked while another command is active.\nACRX_CMD_TRANSPARENT (1) -- Command can be invoked while another command is active.\nThe secondary flags are\nACRX_CMD_USEPICKSET (2) -- When the pickfirst set is retrieved it is cleared within AutoCAD. Command will be able to retrieve the pickfirst set. Command cannot retrieve or set grips.\nACRX_CMD_REDRAW (4) -- When the pickfirst set or grip set is retrieved, neither will be cleared within AutoCAD. Command can retrieve the pickfirst set and the grip set.\nIf both ACRX_CMD_USEPICKSET and ACRX_CMD_REDRAW are set, the effect is the same as if just ACRX_CMD_REDRAW is set. For more information about the flags, see the “Command Stack” in the ObjectARX Reference.")

(setq *autolisp-reference-value* (cons (cons "cmd-flags" *autolisp-reference-string*) *autolisp-reference-value*))

(setq *autolisp-reference-string* "Type: String\nA local name for the command (defaults to global-name).")

(setq *autolisp-reference-value* (cons (cons "local-name" *autolisp-reference-string*) *autolisp-reference-value*))

(setq *autolisp-reference-string* "Type: Subroutine or Symbol\nA symbol naming an AutoLISP function with zero arguments.")

(setq *autolisp-reference-value* (cons (cons "func-sym" *autolisp-reference-string*) *autolisp-reference-value*))

(setq *autolisp-reference-string* "Type: String\nThe global name for the command.")

(setq *autolisp-reference-value* (cons (cons "global-name" *autolisp-reference-string*) *autolisp-reference-value*))

(setq *autolisp-reference-entry* (cons (cons 'arguments *autolisp-reference-value*) *autolisp-reference-entry*))

(setq *autolisp-reference-value* "(vlax-add-cmd global-name func-sym [local-name cmd-flags])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Application-Handling" "Query and Command"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Adds commands to the AutoCAD built-in command set")

(setq *autolisp-reference-entry* (cons (cons 'summary *autolisp-reference-value*) *autolisp-reference-entry*))

(setq *autolisp-reference-value* "vlax-add-cmd (AutoLISP/ActiveX)")

(setq *autolisp-reference-entry* (cons (cons 'title *autolisp-reference-value*) *autolisp-reference-entry*))

(setq *autolisp-reference-value* "vlax-add-cmd")

(setq *autolisp-reference-entry* (cons (cons 'name *autolisp-reference-value*) *autolisp-reference-entry*))

(setq *autolisp-reference-parts* (cons (list (cons "vlax-add-cmd" *autolisp-reference-entry*)) *autolisp-reference-parts*))

(setq *autolisp-reference-parts*
  (cons
    '(("vlax-create-object" .
          ((name . "vlax-create-object")
           (title . "vlax-create-object (AutoLISP/ActiveX)")
           (summary . "Creates a new instance of an application object")
           (source-kind . "AutoLISP/ActiveX")
           (alphabetic-group . "V")
           (feature-groups . ("Drawing Object Functions Reference (AutoLISP/ActiveX)"))
           (supported-platforms . "Windows only")
           (signature . nil)
           (arguments . nil)
           (return-values . "Type: VLA-object\nThe application object.")
           (release-information . nil)
           (history . nil)
           (examples . "Create an instance of a Microsoft Excel application:\n\n(vlax-create-object \"Excel.Application\")\n#<VLA-OBJECT _Application 0017b894>")
           (url . "https://help.autodesk.com/cloudhelp/2023/ENU/AutoCAD-AutoLISP-Reference/files/GUID-D5A6811A-F110-49DD-AF83-1F64773D7DC1.htm")
           (guid . "GUID-D5A6811A-F110-49DD-AF83-1F64773D7DC1"))))
    *autolisp-reference-parts*))

(setq *autolisp-reference-parts*
  (cons
    '(("vlax-curve-getArea" .
          ((name . "vlax-curve-getArea")
           (title . "vlax-curve-getArea (AutoLISP/ActiveX)")
           (summary . "Returns the area inside the curve")
           (source-kind . "AutoLISP/ActiveX")
           (alphabetic-group . "V")
           (feature-groups . ("Curve Measurement Functions Reference (AutoLISP/ActiveX)"))
           (supported-platforms . "Windows only")
           (signature . "(vlax-curve-getArea curve-obj)")
           (arguments . (("curve-obj" . "Type: VLA-object\nThe object to be measured.")))
           (return-values . "Type: Real or nil\nA numeric value representing the area of the curve, if successful; otherwise nil.")
           (release-information . nil)
           (history . nil)
           (examples . "Assume the curve being measured is the ellipse in the following drawing:\n\nSample curve (ellipse) for vlax-curve-getArea\n\nThe ellipseObj variable points to the ellipse VLA-object.\n\nThe following command obtains the area of the curve:\n\n(vlax-curve-getArea ellipseObj)\n4.712393")
           (url . "https://help.autodesk.com/cloudhelp/2023/ENU/AutoCAD-AutoLISP-Reference/files/GUID-93C0A361-465A-400F-B26E-04E914242290.htm")
           (guid . "GUID-93C0A361-465A-400F-B26E-04E914242290"))))
    *autolisp-reference-parts*))

(setq *autolisp-reference-entry* nil)

(setq *autolisp-reference-value* "GUID-90F585FE-D5C8-4C08-AFC7-A09A697EA52A")

(setq *autolisp-reference-entry* (cons (cons 'guid *autolisp-reference-value*) *autolisp-reference-entry*))

(setq *autolisp-reference-value* "https://help.autodesk.com/cloudhelp/2023/ENU/AutoCAD-AutoLISP-Reference/files/GUID-90F585FE-D5C8-4C08-AFC7-A09A697EA52A.htm")

(setq *autolisp-reference-entry* (cons (cons 'url *autolisp-reference-value*) *autolisp-reference-entry*))

(setq *autolisp-reference-value* "Assume that the curve being measured is the arc in the following drawing:\n\nReturn the closest point on the arc to the coordinates 6.0, 0.5:\n\n(vlax-curve-getClosestPointTo arcObj '(6.0 0.5 0.0))\n(6.0 1.5 0.0)\n\nReturn the closest point on the arc to the coordinates 6.0, 0.5, after extending the arc:\n\n(vlax-curve-getClosestPointTo arcObj '(6.0 0.5 0.0) T)\n(5.7092 0.681753 0.0)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nA 3D point representing a point on the curve, if successful; otherwise nil.")

(setq *autolisp-reference-entry* (cons (cons 'return-values *autolisp-reference-value*) *autolisp-reference-entry*))

(setq *autolisp-reference-value* nil)

(setq *autolisp-reference-string* "Type: T\nIf specified and not nil, vlax-curve-getClosestPointTo extends the curve when searching for the nearest point.")

(setq *autolisp-reference-value* (cons (cons "extend" *autolisp-reference-string*) *autolisp-reference-value*))

(setq *autolisp-reference-string* "Type: List\nA point (in WCS) for which to find the nearest point on the curve.")

(setq *autolisp-reference-value* (cons (cons "givenPnt" *autolisp-reference-string*) *autolisp-reference-value*))

(setq *autolisp-reference-string* "Type: VLA-object\nThe object to be measured.")

(setq *autolisp-reference-value* (cons (cons "curve-obj" *autolisp-reference-string*) *autolisp-reference-value*))

(setq *autolisp-reference-entry* (cons (cons 'arguments *autolisp-reference-value*) *autolisp-reference-entry*))

(setq *autolisp-reference-value* "(vlax-curve-getClosestPointTo curve-obj givenPnt [extend])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Curve Measurement Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns the point (in WCS) on a curve that is nearest to the specified point")

(setq *autolisp-reference-entry* (cons (cons 'summary *autolisp-reference-value*) *autolisp-reference-entry*))

(setq *autolisp-reference-value* "vlax-curve-getClosestPointTo (AutoLISP/ActiveX)")

(setq *autolisp-reference-entry* (cons (cons 'title *autolisp-reference-value*) *autolisp-reference-entry*))

(setq *autolisp-reference-value* "vlax-curve-getClosestPointTo")

(setq *autolisp-reference-entry* (cons (cons 'name *autolisp-reference-value*) *autolisp-reference-entry*))

(setq *autolisp-reference-parts* (cons (list (cons "vlax-curve-getClosestPointTo" *autolisp-reference-entry*)) *autolisp-reference-parts*))

(setq *autolisp-reference-parts*
  (cons
    '(("vlax-curve-getClosestPointToProjection" .
          ((name . "vlax-curve-getClosestPointToProjection")
           (title . "vlax-curve-getClosestPointToProjection (AutoLISP/ActiveX)")
           (summary . "Returns the closest point (in WCS) on a curve after projecting the curve onto a plane")
           (source-kind . "AutoLISP/ActiveX")
           (alphabetic-group . "V")
           (feature-groups . ("Curve Measurement Functions Reference (AutoLISP/ActiveX)"))
           (supported-platforms . "Windows only")
           (signature . "(vlax-curve-getClosestPointToProjection curve-obj givenPnt normal [extend])")
           (arguments . (("curve-obj" . "Type: VLA-object\nThe object to be measured.")
                           ("givenPnt" . "Type: List\nA point (in WCS) for which to find the nearest point on the curve.")
                           ("normal" . "Type: List\nA normal vector (in WCS) for the plane to project onto.")
                           ("extend" . "Type: T\nIf specified and not nil, vlax-curve-getClosestPointToProjection extends the curve when searching for the nearest point.")))
           (return-values . "Type: List or nil\nA 3D point representing a point on the curve, if successful; otherwise nil.")
           (release-information . nil)
           (history . nil)
           (examples . nil)
           (url . "https://help.autodesk.com/cloudhelp/2023/ENU/AutoCAD-AutoLISP-Reference/files/GUID-23A1B8CE-9FF5-482C-AF32-3EE48784B905.htm")
           (guid . "GUID-23A1B8CE-9FF5-482C-AF32-3EE48784B905"))))
    *autolisp-reference-parts*))

(setq *autolisp-reference-entry* nil)

(setq *autolisp-reference-value* "GUID-8FF6D3D5-7EA5-4E9A-8A61-295C0562E7AE")

(setq *autolisp-reference-entry* (cons (cons 'guid *autolisp-reference-value*) *autolisp-reference-entry*))

(setq *autolisp-reference-value* "https://help.autodesk.com/cloudhelp/2023/ENU/AutoCAD-AutoLISP-Reference/files/GUID-8FF6D3D5-7EA5-4E9A-8A61-295C0562E7AE.htm")

(setq *autolisp-reference-entry* (cons (cons 'url *autolisp-reference-value*) *autolisp-reference-entry*))

(setq *autolisp-reference-value* "Assume that splineObj points to the spline in the following drawing:\n\nSample curve (spline) for vlax-curve-getDistAtParam\n\nObtain the start parameter of the curve:\n\n(setq startSpline (vlax-curve-getStartParam splineObj))\n0.0\n\nThe curve starts at parameter 0.\n\nObtain the end parameter of the curve:\n\n(setq endSpline (vlax-curve-getEndParam splineObj))\n17.1546\n\nThe curve's end parameter is 17.1546.\n\nDetermine the distance to the parameter midway along the curve:\n\n(vlax-curve-getDistAtParam splineObj\n   ( / (- endspline startspline) 2))\n8.99417\n\nThe distance from the start to the middle of the curve is 8.99417.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Real or nil\nA number that is the length up to the specified parameter, if successful; otherwise nil.")

(setq *autolisp-reference-entry* (cons (cons 'return-values *autolisp-reference-value*) *autolisp-reference-entry*))

(setq *autolisp-reference-value* nil)

(setq *autolisp-reference-string* "Type: Integer or Real\nA number specifying a parameter on the curve.")

(setq *autolisp-reference-value* (cons (cons "param" *autolisp-reference-string*) *autolisp-reference-value*))

(setq *autolisp-reference-string* "Type: VLA-object\nThe object to be measured.")

(setq *autolisp-reference-value* (cons (cons "curve-obj" *autolisp-reference-string*) *autolisp-reference-value*))

(setq *autolisp-reference-entry* (cons (cons 'arguments *autolisp-reference-value*) *autolisp-reference-entry*))

(setq *autolisp-reference-value* "(vlax-curve-getDistAtParam curve-obj param)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Curve Measurement Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns the length of the curve's segment from the curve's beginning to the specified parameter")

(setq *autolisp-reference-entry* (cons (cons 'summary *autolisp-reference-value*) *autolisp-reference-entry*))

(setq *autolisp-reference-value* "vlax-curve-getDistAtParam (AutoLISP/ActiveX)")

(setq *autolisp-reference-entry* (cons (cons 'title *autolisp-reference-value*) *autolisp-reference-entry*))

(setq *autolisp-reference-value* "vlax-curve-getDistAtParam")

(setq *autolisp-reference-entry* (cons (cons 'name *autolisp-reference-value*) *autolisp-reference-entry*))

(setq *autolisp-reference-parts* (cons (list (cons "vlax-curve-getDistAtParam" *autolisp-reference-entry*)) *autolisp-reference-parts*))

(setq *autolisp-reference-parts*
  (cons
    '(("vlax-curve-getDistAtPoint" .
          ((name . "vlax-curve-getDistAtPoint")
           (title . "vlax-curve-getDistAtPoint (AutoLISP/ActiveX)")
           (summary . "Returns the length of the curve's segment between the curve's start point and the specified point")
           (source-kind . "AutoLISP/ActiveX")
           (alphabetic-group . "V")
           (feature-groups . ("Curve Measurement Functions Reference (AutoLISP/ActiveX)"))
           (supported-platforms . "Windows only")
           (signature . "(vlax-curve-getDistAtPoint curve-obj point)")
           (arguments . (("curve-obj" . "Type: VLA-object\nThe object to be measured.")
                           ("point" . "Type: List\nA 3D point list (in WCS) on curve-obj.")))
           (return-values . "Type: Real or nil\nA number if successful; otherwise nil.")
           (release-information . nil)
           (history . nil)
           (examples . "Set OSNAP to tangent and select the point where the line is tangent to the curve:\n\n(setq selPt (getpoint))\n(4.91438 6.04738 0.0)\n\nDetermine the distance from the start of the curve to the selected point:\n\n(vlax-curve-getDistAtPoint splineObj selpt)\n5.17769")
           (url . "https://help.autodesk.com/cloudhelp/2023/ENU/AutoCAD-AutoLISP-Reference/files/GUID-627E64B0-B34C-4E7A-AC69-745EDAC1080D.htm")
           (guid . "GUID-627E64B0-B34C-4E7A-AC69-745EDAC1080D"))))
    *autolisp-reference-parts*))

(setq *autolisp-reference-parts*
  (cons
    '(("vlax-curve-getEndParam" .
          ((name . "vlax-curve-getEndParam")
           (title . "vlax-curve-getEndParam (AutoLISP/ActiveX)")
           (summary . "Returns the parameter of the endpoint of the curve")
           (source-kind . "AutoLISP/ActiveX")
           (alphabetic-group . "V")
           (feature-groups . ("Curve Measurement Functions Reference (AutoLISP/ActiveX)"))
           (supported-platforms . "Windows only")
           (signature . "(vlax-curve-getEndParam curve-obj)")
           (arguments . (("curve-obj" . "Type: VLA-object\nThe object to be measured.")))
           (return-values . "Type: Real or nil\nA number representing an end parameter, if successful; otherwise nil.")
           (release-information . nil)
           (history . nil)
           (examples . "The following function call returns the end parameter of the curve:\n\n(vlax-curve-getendparam ellipseObj)\n6.28319\n\nThe end parameter is 6.28319 (twice pi).")
           (url . "https://help.autodesk.com/cloudhelp/2023/ENU/AutoCAD-AutoLISP-Reference/files/GUID-B939A11A-DF89-4450-B520-11D59BD2A126.htm")
           (guid . "GUID-B939A11A-DF89-4450-B520-11D59BD2A126"))))
    *autolisp-reference-parts*))

(setq *autolisp-reference-parts*
  (cons
    '(("vlax-curve-getEndPoint" .
          ((name . "vlax-curve-getEndPoint")
           (title . "vlax-curve-getEndPoint (AutoLISP/ActiveX)")
           (summary . "Returns the endpoint (in WCS) of the curve")
           (source-kind . "AutoLISP/ActiveX")
           (alphabetic-group . "V")
           (feature-groups . ("Curve Measurement Functions Reference (AutoLISP/ActiveX)"))
           (supported-platforms . "Windows only")
           (signature . "(vlax-curve-getEndPoint curve-obj)")
           (arguments . (("curve-obj" . "Type: VLA-object\nThe object to be measured.")))
           (return-values . "Type: List or nil\nA 3D point representing an endpoint, if successful; otherwise nil.")
           (release-information . nil)
           (history . nil)
           (examples . "(vlax-curve-getEndPoint ellipseObj)\n(2.0 2.0 0.0)")
           (url . "https://help.autodesk.com/cloudhelp/2023/ENU/AutoCAD-AutoLISP-Reference/files/GUID-11309952-C617-4467-85E8-7EBE949F2730.htm")
           (guid . "GUID-11309952-C617-4467-85E8-7EBE949F2730"))))
    *autolisp-reference-parts*))

(setq *autolisp-reference-parts*
  (cons
    '(("vlax-curve-getFirstDeriv" .
          ((name . "vlax-curve-getFirstDeriv")
           (title . "vlax-curve-getFirstDeriv (AutoLISP/ActiveX)")
           (summary . "Returns the first derivative (in WCS) of a curve at the specified location")
           (source-kind . "AutoLISP/ActiveX")
           (alphabetic-group . "V")
           (feature-groups . ("Curve Measurement Functions Reference (AutoLISP/ActiveX)"))
           (supported-platforms . "Windows only")
           (signature . "(vlax-curve-getFirstDeriv curve-obj param)")
           (arguments . (("curve-obj" . "Type: VLA-object\nThe object to be measured.")
                           ("param" . "Type: Integer or Real\nA number specifying a parameter on the curve.")))
           (return-values . "Type: List or nil\nA 3D vector, if successful; otherwise nil.")
           (release-information . nil)
           (history . nil)
           (examples . "Obtain the start parameter of the curve:\n\n(setq startSpline (vlax-curve-getStartParam splineObj))\n0.0\n\nObtain the end parameter of the curve:\n\n(setq endSpline (vlax-curve-getEndParam splineObj))\n17.1546\n\nDetermine the first derivative at the parameter midway along the curve:\n\n (vlax-curve-getFirstDeriv splineObj\n   ( / (- endspline startspline) 2))\n(0.422631 -1.0951 0.0)")
           (url . "https://help.autodesk.com/cloudhelp/2023/ENU/AutoCAD-AutoLISP-Reference/files/GUID-37282EB1-D47C-4039-B1AF-744EB5B53F25.htm")
           (guid . "GUID-37282EB1-D47C-4039-B1AF-744EB5B53F25"))))
    *autolisp-reference-parts*))

(setq *autolisp-reference-parts*
  (cons
    '(("vlax-curve-getParamAtDist" .
          ((name . "vlax-curve-getParamAtDist")
           (title . "vlax-curve-getParamAtDist (AutoLISP/ActiveX)")
           (summary . "Returns the parameter of a curve at the specified distance from the beginning of the curve")
           (source-kind . "AutoLISP/ActiveX")
           (alphabetic-group . "V")
           (feature-groups . ("Curve Measurement Functions Reference (AutoLISP/ActiveX)"))
           (supported-platforms . "Windows only")
           (signature . "(vlax-curve-getParamAtDist curve-obj dist)")
           (arguments . (("curve-obj" . "Type: VLA-object\nThe object to be measured.")
                           ("dist" . "Type: Integer or Real\nA number specifying the distance from the beginning of the curve.")))
           (return-values . "Type: Real or nil\nA number representing a parameter, if successful; otherwise nil.")
           (release-information . nil)
           (history . nil)
           (examples . "(vlax-curve-getParamAtDist splineObj 1.0)\n0.685049")
           (url . "https://help.autodesk.com/cloudhelp/2023/ENU/AutoCAD-AutoLISP-Reference/files/GUID-4F02FF68-0D68-453D-A63E-2CB96DB62B05.htm")
           (guid . "GUID-4F02FF68-0D68-453D-A63E-2CB96DB62B05"))))
    *autolisp-reference-parts*))

(setq *autolisp-reference-parts*
  (cons
    '(("vlax-curve-getParamAtPoint" .
          ((name . "vlax-curve-getParamAtPoint")
           (title . "vlax-curve-getParamAtPoint (AutoLISP/ActiveX)")
           (summary . "Returns the parameter of the curve at the point")
           (source-kind . "AutoLISP/ActiveX")
           (alphabetic-group . "V")
           (feature-groups . ("Curve Measurement Functions Reference (AutoLISP/ActiveX)"))
           (supported-platforms . "Windows only")
           (signature . "(vlax-curve-getParamAtPoint curve-obj point)")
           (arguments . (("curve-obj" . "Type: VLA-object\nThe object to be measured.")
                           ("point" . "Type: List\nA 3D point (in WCS) on curve-obj.")))
           (return-values . "Type: Real or nil\nA number representing a parameter, if successful; otherwise nil.")
           (release-information . nil)
           (history . nil)
           (examples . "Assuming that ellipseObj points to the ellipse shown in the example for vlax-curve-getArea, set OSNAP to tangent and select the point where the line is tangent to the ellipse:\n\n(setq selPt (getpoint))\n(7.55765 5.55066 0.0)\n\nGet the parameter value at the selected point:\n\n(vlax-curve-getParamAtPoint ellipseObj selPt)\n4.58296")
           (url . "https://help.autodesk.com/cloudhelp/2023/ENU/AutoCAD-AutoLISP-Reference/files/GUID-1827742B-21DE-4454-90A0-19551DE79B5A.htm")
           (guid . "GUID-1827742B-21DE-4454-90A0-19551DE79B5A"))))
    *autolisp-reference-parts*))

(setq *autolisp-reference-parts*
  (cons
    '(("vlax-curve-getPointAtDist" .
          ((name . "vlax-curve-getPointAtDist")
           (title . "vlax-curve-getPointAtDist (AutoLISP/ActiveX)")
           (summary . "Returns the point (in WCS) along a curve at the distance specified by the user")
           (source-kind . "AutoLISP/ActiveX")
           (alphabetic-group . "V")
           (feature-groups . ("Curve Measurement Functions Reference (AutoLISP/ActiveX)"))
           (supported-platforms . "Windows only")
           (signature . "(vlax-curve-getPointAtDist curve-obj dist)")
           (arguments . (("curve-obj" . "Type: VLA-object\nThe object to be measured.")
                           ("dist" . "Type: Real\nThe distance along the curve from the beginning of the curve to the location of the specified point.")))
           (return-values . "Type: List or nil\nA 3D point representing a point on the curve, if successful; otherwise nil.")
           (release-information . nil)
           (history . nil)
           (examples . "Assuming that splineObj points to the spline shown in the example for vlax-curve-getDistAtParam, determine the point at a distance of 1.0 from the beginning of the spline:\n\n(vlax-curve-getPointAtDist splineObj 1.0)\n(2.24236 2.99005 0.0)")
           (url . "https://help.autodesk.com/cloudhelp/2023/ENU/AutoCAD-AutoLISP-Reference/files/GUID-F41FB58A-4645-404E-98B7-D4978A9A790B.htm")
           (guid . "GUID-F41FB58A-4645-404E-98B7-D4978A9A790B"))))
    *autolisp-reference-parts*))

(setq *autolisp-reference-parts*
  (cons
    '(("vlax-curve-getPointAtParam" .
          ((name . "vlax-curve-getPointAtParam")
           (title . "vlax-curve-getPointAtParam (AutoLISP/ActiveX)")
           (summary . "Returns the point at the specified parameter value along a curve")
           (source-kind . "AutoLISP/ActiveX")
           (alphabetic-group . "V")
           (feature-groups . ("Curve Measurement Functions Reference (AutoLISP/ActiveX)"))
           (supported-platforms . "Windows only")
           (signature . "(vlax-curve-getPointAtParam curve-obj param)")
           (arguments . (("curve-obj" . "Type: VLA-object\nThe object to be measured.")
                           ("param" . "Type: Integer or Real\nA number specifying a parameter on the curve.")))
           (return-values . "Type: List or nil\nA 3D point representing a point on the curve, if successful; otherwise nil.")
           (release-information . nil)
           (history . nil)
           (examples . "For the following example, assume that splineObj points to the spline shown in the example for vlax-curve-getDistAtParam.\n\nObtain the start parameter of the curve:\n\n(setq startSpline (vlax-curve-getStartParam splineObj))\n0.0\n\nObtain the end parameter of the curve:\n\n(setq endSpline (vlax-curve-getEndParam splineObj))\n17.1546\n\nDetermine the point at the parameter midway along the curve:\n\n(vlax-curve-getPointAtParam splineObj\n   ( / (- endspline startspline) 2))\n(6.71386 2.82748 0.0)")
           (url . "https://help.autodesk.com/cloudhelp/2023/ENU/AutoCAD-AutoLISP-Reference/files/GUID-B506C696-DBDA-466B-9EF8-1AF3B1A485F8.htm")
           (guid . "GUID-B506C696-DBDA-466B-9EF8-1AF3B1A485F8"))))
    *autolisp-reference-parts*))

(setq *autolisp-reference-parts*
  (cons
    '(("vlax-curve-getSecondDeriv" .
          ((name . "vlax-curve-getSecondDeriv")
           (title . "vlax-curve-getSecondDeriv (AutoLISP/ActiveX)")
           (summary . "Returns the second derivative (in WCS) of a curve at the specified location")
           (source-kind . "AutoLISP/ActiveX")
           (alphabetic-group . "V")
           (feature-groups . ("Curve Measurement Functions Reference (AutoLISP/ActiveX)"))
           (supported-platforms . "Windows only")
           (signature . "(vlax-curve-getSecondDeriv curve-obj param)")
           (arguments . (("curve-obj" . "Type: VLA-object\nThe object to be measured.")
                           ("param" . "Type: Integer or Real\nA number specifying a parameter on the curve.")))
           (return-values . "Type: List or nil\nA 3D vector, if successful; otherwise nil.")
           (release-information . nil)
           (history . nil)
           (examples . "For the following example, assume that splineObj points to the spline shown in the example of the vlax-curve-getDistAtParam function.\n\nObtain the start parameter of the curve:\n\n(setq startSpline (vlax-curve-getStartParam splineObj))\n0.0\n\nObtain the end parameter of the curve:\n\n(setq endSpline (vlax-curve-getEndParam splineObj))\n17.1546\n\nDetermine the second derivative at the parameter midway along the curve:\n\n(vlax-curve-getSecondDeriv splineObj\n   ( / (- endspline startspline) 2))\n(0.0165967 0.150848 0.0)")
           (url . "https://help.autodesk.com/cloudhelp/2023/ENU/AutoCAD-AutoLISP-Reference/files/GUID-E1C78CD1-2347-4A2B-B054-62149738F9A6.htm")
           (guid . "GUID-E1C78CD1-2347-4A2B-B054-62149738F9A6"))))
    *autolisp-reference-parts*))

(setq *autolisp-reference-parts*
  (cons
    '(("vlax-curve-getStartParam" .
          ((name . "vlax-curve-getStartParam")
           (title . "vlax-curve-getStartParam (AutoLISP/ActiveX)")
           (summary . "Returns the start parameter on the curve")
           (source-kind . "AutoLISP/ActiveX")
           (alphabetic-group . "V")
           (feature-groups . ("Curve Measurement Functions Reference (AutoLISP/ActiveX)"))
           (supported-platforms . "Windows only")
           (signature . "(vlax-curve-getStartParam curve-obj)")
           (arguments . (("curve-obj" . "Type: VLA-object\nThe object to be measured.")))
           (return-values . "Type: Real or nil\nA number representing the start parameter, if successful; otherwise nil.")
           (release-information . nil)
           (history . nil)
           (examples . "Assuming that ellipseObj points to the ellipse shown in the example for vlax-curve-getArea, determine the start parameter of the curve:\n\n(vlax-curve-getstartparam ellipseObj)\n0.0")
           (url . "https://help.autodesk.com/cloudhelp/2023/ENU/AutoCAD-AutoLISP-Reference/files/GUID-854C3C4D-1305-4920-9E42-D9ACB9E4363C.htm")
           (guid . "GUID-854C3C4D-1305-4920-9E42-D9ACB9E4363C"))))
    *autolisp-reference-parts*))

(setq *autolisp-reference-parts*
  (cons
    '(("vlax-curve-getStartPoint" .
          ((name . "vlax-curve-getStartPoint")
           (title . "vlax-curve-getStartPoint (AutoLISP/ActiveX)")
           (summary . "Returns the start point (in WCS) of the curve")
           (source-kind . "AutoLISP/ActiveX")
           (alphabetic-group . "V")
           (feature-groups . ("Curve Measurement Functions Reference (AutoLISP/ActiveX)"))
           (supported-platforms . "Windows only")
           (signature . "(vlax-curve-getStartPoint curve-obj)")
           (arguments . (("curve-obj" . "Type: VLA-object\nThe object to be measured.")))
           (return-values . "Type: List or nil\nA 3D point representing the start point, if successful; otherwise nil.")
           (release-information . nil)
           (history . nil)
           (examples . "Get the start point of the ellipse.\n\n(vlax-curve-getStartPoint ellipseObj)\n(2.0 2.0 0.0)\n\nFor an ellipse, the start points and endpoints are the same.\n\nObtain the start point of the spline used to demonstrate vlax-curve-getDistAtParam:\n\n(vlax-curve-getStartPoint splineObj)\n(1.73962 2.12561 0.0)")
           (url . "https://help.autodesk.com/cloudhelp/2023/ENU/AutoCAD-AutoLISP-Reference/files/GUID-AA1C450F-AA6E-4B05-AFB3-989AD91ADBFC.htm")
           (guid . "GUID-AA1C450F-AA6E-4B05-AFB3-989AD91ADBFC"))))
    *autolisp-reference-parts*))

(setq *autolisp-reference-parts*
  (cons
    '(("vlax-curve-isClosed" .
          ((name . "vlax-curve-isClosed")
           (title . "vlax-curve-isClosed (AutoLISP/ActiveX)")
           (summary . "Determines if the specified curve is closed (that is, the start point is the same as the endpoint)")
           (source-kind . "AutoLISP/ActiveX")
           (alphabetic-group . "V")
           (feature-groups . ("Curve Measurement Functions Reference (AutoLISP/ActiveX)"))
           (supported-platforms . "Windows only")
           (signature . "(vlax-curve-isClosed curve-obj)")
           (arguments . (("curve-obj" . "Type: VLA-object\nThe object to be tested.")))
           (return-values . "Type: T or nil\nT if the curve is closed; otherwise nil.")
           (release-information . nil)
           (history . nil)
           (examples . "Determine if the ellipse used to demonstrate vlax-curve-getArea is closed:\n\n(vlax-curve-isClosed ellipseObj)\nT\n\nDetermine if the spline used to demonstrate vlax-curve-getDistAtParam is closed:\n\n(vlax-curve-isClosed splineObj)\nnil")
           (url . "https://help.autodesk.com/cloudhelp/2023/ENU/AutoCAD-AutoLISP-Reference/files/GUID-DC3C19D3-D0EA-4638-B8AB-E3A057B66D1F.htm")
           (guid . "GUID-DC3C19D3-D0EA-4638-B8AB-E3A057B66D1F"))))
    *autolisp-reference-parts*))

(setq *autolisp-reference-parts*
  (cons
    '(("vlax-curve-isPeriodic" .
          ((name . "vlax-curve-isPeriodic")
           (title . "vlax-curve-isPeriodic (AutoLISP/ActiveX)")
           (summary . "Determines if the specified curve has an infinite range in both directions and there is a period value dT, such that a point on the curve at (u + dT) = point on curve (u), for any parameter u")
           (source-kind . "AutoLISP/ActiveX")
           (alphabetic-group . "V")
           (feature-groups . ("Curve Measurement Functions Reference (AutoLISP/ActiveX)"))
           (supported-platforms . "Windows only")
           (signature . "(vlax-curve-isPeriodic curve-obj)")
           (arguments . (("curve-obj" . "Type: VLA-object\nThe object to be tested.")))
           (return-values . "Type: T or nil\nT if the curve is periodic; otherwise nil.")
           (release-information . nil)
           (history . nil)
           (examples . "Determine if the ellipse used to demonstrate vlax-curve-getArea is periodic:\n\n(vlax-curve-isPeriodic ellipseObj)\nT\n\nDetermine if the spline used to demonstrate vlax-curve-getDistAtParam is periodic:\n\n(vlax-curve-isPeriodic splineObj)\nnil")
           (url . "https://help.autodesk.com/cloudhelp/2023/ENU/AutoCAD-AutoLISP-Reference/files/GUID-0A082EE2-ACE0-49CE-981D-2665738C7DC2.htm")
           (guid . "GUID-0A082EE2-ACE0-49CE-981D-2665738C7DC2"))))
    *autolisp-reference-parts*))

(setq *autolisp-reference-parts*
  (cons
    '(("vlax-curve-isPlanar" .
          ((name . "vlax-curve-isPlanar")
           (title . "vlax-curve-isPlanar (AutoLISP/ActiveX)")
           (summary . "Determines if there is a plane that contains the curve")
           (source-kind . "AutoLISP/ActiveX")
           (alphabetic-group . "V")
           (feature-groups . ("Curve Measurement Functions Reference (AutoLISP/ActiveX)"))
           (supported-platforms . "Windows only")
           (signature . "(vlax-curve-isPlanar curve-obj)")
           (arguments . (("curve-obj" . "Type: VLA-object\nThe object to be tested.")))
           (return-values . "Type: T or nil\nT if there is a plane that contains the curve; otherwise nil.")
           (release-information . nil)
           (history . nil)
           (examples . "Determine if there is a plane containing the ellipse used to demonstrate vlax-curve-getArea:\n\n(vlax-curve-isPlanar ellipseObj)\nT\n\nDetermine if there is a plane containing the spline used to demonstrate vlax-curve-getDistAtParam:\n\n(vlax-curve-isPeriodic splineObj)\nnil")
           (url . "https://help.autodesk.com/cloudhelp/2023/ENU/AutoCAD-AutoLISP-Reference/files/GUID-798B0177-0B90-4393-AF9D-C1D4607A0E7F.htm")
           (guid . "GUID-798B0177-0B90-4393-AF9D-C1D4607A0E7F"))))
    *autolisp-reference-parts*))

(setq *autolisp-reference-entry* nil)

(setq *autolisp-reference-value* "GUID-BCE56B30-54A6-42F9-8910-81AF2B7B9AA8")

(setq *autolisp-reference-entry* (cons (cons 'guid *autolisp-reference-value*) *autolisp-reference-entry*))

(setq *autolisp-reference-value* "https://help.autodesk.com/cloudhelp/2023/ENU/AutoCAD-AutoLISP-Reference/files/GUID-BCE56B30-54A6-42F9-8910-81AF2B7B9AA8.htm")

(setq *autolisp-reference-entry* (cons (cons 'url *autolisp-reference-value*) *autolisp-reference-entry*))

(setq *autolisp-reference-value* "(setq aa (vlax-get-acad-object))\n#<VLA-OBJECT IAcadApplication 00b3b91c>\n\n(vlax-dump-object aa)\n; IAcadApplication: AutoCAD Application Interface\n; Property values:\n;   ActiveDocument (RO) = #<VLA-OBJECT IAcadDocument 01b52fac>\n;   Application (RO) = #<VLA-OBJECT IAcadApplication 00b3b91c>\n;   Caption (RO) = \"AutoCAD - [Drawing.dwg]\"\n.\n.\n.\nT\n\nList an object's properties and the methods that apply to the object:\n\n(vlax-dump-object aa T)\n; IAcadApplication: AutoCAD Application Interface\n; Property values:\n;   ActiveDocument (RO) = #<VLA-OBJECT IAcadDocument 01b52fac>\n;   Application (RO) = #<VLA-OBJECT IAcadApplication 00b3b91c>\n;   Caption (RO) = \"AutoCAD - [Drawing.dwg]\"\n.\n.\n.\n; Methods supported:\n;   EndUndoMark ()\n;   Eval (1)\n;   GetInterfaceObject (1)\n;   ListAds ()\n;   ListArx ()\n.\n.\n.\nT")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or error\nT, if successful. If an invalid object name is supplied, vlax-dump-object displays an error message.")

(setq *autolisp-reference-entry* (cons (cons 'return-values *autolisp-reference-value*) *autolisp-reference-entry*))

(setq *autolisp-reference-value* nil)

(setq *autolisp-reference-string* "Type: T or nil\nIf specified and not nil, vlax-dump-object also lists all methods that apply to obj.")

(setq *autolisp-reference-value* (cons (cons "flag" *autolisp-reference-string*) *autolisp-reference-value*))

(setq *autolisp-reference-string* "Type: VLA-object\nAn object.")

(setq *autolisp-reference-value* (cons (cons "obj" *autolisp-reference-string*) *autolisp-reference-value*))

(setq *autolisp-reference-entry* (cons (cons 'arguments *autolisp-reference-value*) *autolisp-reference-entry*))

(setq *autolisp-reference-value* "(vlax-dump-object obj [flag])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Drawing Object Functions Reference (AutoLISP/ActiveX)" "Object-Handling" "Object-Handling Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Lists an object's properties, and optionally, the methods that apply to the object")

(setq *autolisp-reference-entry* (cons (cons 'summary *autolisp-reference-value*) *autolisp-reference-entry*))

(setq *autolisp-reference-value* "vlax-dump-object (AutoLISP/ActiveX)")

(setq *autolisp-reference-entry* (cons (cons 'title *autolisp-reference-value*) *autolisp-reference-entry*))

(setq *autolisp-reference-value* "vlax-dump-object")

(setq *autolisp-reference-entry* (cons (cons 'name *autolisp-reference-value*) *autolisp-reference-entry*))

(setq *autolisp-reference-parts* (cons (list (cons "vlax-dump-object" *autolisp-reference-entry*)) *autolisp-reference-parts*))

(setq *autolisp-reference-parts*
  (cons
    '(("vlax-ename->vla-object" .
          ((name . "vlax-ename->vla-object")
           (title . "vlax-ename->vla-object (AutoLISP/ActiveX)")
           (summary . "Transforms an entity to a VLA-object")
           (source-kind . "AutoLISP/ActiveX")
           (alphabetic-group . "V")
           (feature-groups . ("Data Conversion Functions Reference (AutoLISP/ActiveX)"))
           (supported-platforms . "Windows only")
           (signature . "(vlax-ename->vla-object entname)")
           (arguments . (("entname" . "Type: Ename (entity name)\nAn entity name.")))
           (return-values . "Type: VLA-object\nThe object that represents the ename.")
           (release-information . nil)
           (history . nil)
           (examples . "(setq e (car (entsel)))\n<Entity name: 27e0540>\n\n(vlax-ename->vla-object e)\n#<VLA-OBJECT IAcadLWPolyline 03f713a0>")
           (url . "https://help.autodesk.com/cloudhelp/2023/ENU/AutoCAD-AutoLISP-Reference/files/GUID-BD451263-76D5-4A93-B50A-3C27E89A0AD4.htm")
           (guid . "GUID-BD451263-76D5-4A93-B50A-3C27E89A0AD4"))))
    *autolisp-reference-parts*))

(setq *autolisp-reference-parts*
  (cons
    '(("vlax-erased-p" .
          ((name . "vlax-erased-p")
           (title . "vlax-erased-p (AutoLISP/ActiveX)")
           (summary . "Determines whether an object was erased")
           (source-kind . "AutoLISP/ActiveX")
           (alphabetic-group . "V")
           (feature-groups . ("Drawing Object Functions Reference (AutoLISP/ActiveX)" "Object-Handling" "Object-Handling Functions Reference (AutoLISP/ActiveX)"))
           (supported-platforms . "Windows only")
           (signature . "(vlax-erased-p obj)")
           (arguments . (("obj" . "Type: VLA-object\nAn object.")))
           (return-values . nil)
           (release-information . nil)
           (history . nil)
           (examples . "N/A")
           (url . "https://help.autodesk.com/cloudhelp/2023/ENU/AutoCAD-AutoLISP-Reference/files/GUID-423F047A-F8B8-4DD0-ABEC-52E3C7B336B5.htm")
           (guid . "GUID-423F047A-F8B8-4DD0-ABEC-52E3C7B336B5"))))
    *autolisp-reference-parts*))

(setq *autolisp-reference-parts*
  (cons
    '(("vlax-for" .
          ((name . "vlax-for")
           (title . "vlax-for (AutoLISP/ActiveX)")
           (summary . "Iterates through a collection of objects, evaluating each expression")
           (source-kind . "AutoLISP/ActiveX")
           (alphabetic-group . "V")
           (feature-groups . ("Collection Manipulation Functions Reference (AutoLISP/ActiveX)"))
           (supported-platforms . "Windows only")
           (signature . "(vlax-for symbol collection [expression1 [expression2 ...]])")
           (arguments . (("symbol" . "Type: VLA-object\nA symbol to be assigned to each VLA-object in a collection.")
                           ("collection" . "Type: VLA-object\nA VLA-object representing a collection object.")
                           ("expression1, expression2..." . "Type: List, Subroutine, or Symbol\nThe expressions to be evaluated.")))
           (return-values . "Type: Integer, Real, String, List, VLA-object, Variant, Safearray, T, or nil\nThe value of the last expression evaluated for the last object in the collection.")
           (release-information . nil)
           (history . nil)
           (examples . "The following code issues vlax-dump-object on every drawing object in the model space:\n\n(vl-load-com)                        ; load ActiveX support\n(vlax-for for-item\n   (vla-get-modelspace\n        (vla-get-activedocument (vlax-get-acad-object))\n   )\n  (vlax-dump-object for-item)        ; list object properties\n)")
           (url . "https://help.autodesk.com/cloudhelp/2023/ENU/AutoCAD-AutoLISP-Reference/files/GUID-9CB1C7DD-7E25-4F8C-8858-D79FEC043BEC.htm")
           (guid . "GUID-9CB1C7DD-7E25-4F8C-8858-D79FEC043BEC"))))
    *autolisp-reference-parts*))

(setq *autolisp-reference-parts*
  (cons
    '(("vlax-get-acad-object" .
          ((name . "vlax-get-acad-object")
           (title . "vlax-get-acad-object (AutoLISP/ActiveX)")
           (summary . "Retrieves the top level AutoCAD application object for the current AutoCAD session")
           (source-kind . "AutoLISP/ActiveX")
           (alphabetic-group . "V")
           (feature-groups . ("Drawing Object Functions Reference (AutoLISP/ActiveX)" "Object-Handling" "Object-Handling Functions Reference (AutoLISP/ActiveX)"))
           (supported-platforms . "Windows only")
           (signature . "(vlax-get-acad-object)")
           (arguments . nil)
           (return-values . "Type: VLA-object\nAn object.")
           (release-information . nil)
           (history . nil)
           (examples . "(setq aa (vlax-get-acad-object))\n#<VLA-OBJECT IAcadApplication 00b3b91c>")
           (url . "https://help.autodesk.com/cloudhelp/2023/ENU/AutoCAD-AutoLISP-Reference/files/GUID-53DB599B-641D-45DD-A201-604942A4596C.htm")
           (guid . "GUID-53DB599B-641D-45DD-A201-604942A4596C"))))
    *autolisp-reference-parts*))

(setq *autolisp-reference-parts*
  (cons
    '(("vlax-get-object" .
          ((name . "vlax-get-object")
           (title . "vlax-get-object (AutoLISP/ActiveX)")
           (summary . "Returns a running instance of an application object")
           (source-kind . "AutoLISP/ActiveX")
           (alphabetic-group . "V")
           (feature-groups . ("Drawing Object Functions Reference (AutoLISP/ActiveX)"))
           (supported-platforms . "Windows only")
           (signature . "(vlax-get-object prog-id)")
           (arguments . (("prog-id" . "Type: String\nIdentifies the desired application object. The format of prog-id is:\nappname.objecttype\nwhere appname is the name of the application and objecttype is the application object. The objecttype may be followed by a version number.\nNote: You can usually find the prog-id for an application in that application's Help.")))
           (return-values . "Type: VLA-object or nil\nThe application object; otherwise nil, if there is no instance of the specified object currently running.")
           (release-information . nil)
           (history . nil)
           (examples . "Obtain the application object for the Excel program:\n\n(vlax-get-object \"Excel.Application\")\n#<VLA-OBJECT _Application 0017bb5c>")
           (url . "https://help.autodesk.com/cloudhelp/2023/ENU/AutoCAD-AutoLISP-Reference/files/GUID-A408BF2E-6C7D-453A-A71A-773FEBACC742.htm")
           (guid . "GUID-A408BF2E-6C7D-453A-A71A-773FEBACC742"))))
    *autolisp-reference-parts*))

(setq *autolisp-reference-parts*
  (cons
    '(("vlax-get-or-create-object" .
          ((name . "vlax-get-or-create-object")
           (title . "vlax-get-or-create-object (AutoLISP/ActiveX)")
           (summary . "Returns a running instance of an application object, or creates a new instance if the application is not currently running")
           (source-kind . "AutoLISP/ActiveX")
           (alphabetic-group . "V")
           (feature-groups . ("Drawing Object Functions Reference (AutoLISP/ActiveX)"))
           (supported-platforms . "Windows only")
           (signature . "(vlax-get-or-create-object prog-id)")
           (arguments . (("prog-id" . "Type: String\nProgrammatic identifier of the desired ActiveX object. The format of prog-id is\n<Vendor>.<Component>.<Version>\nFor example:\nExcel.Application.16")))
           (return-values . "Type: VLA-object\nAn object.")
           (release-information . nil)
           (history . nil)
           (examples . "(vlax-get-or-create-object \"Excel.Application\")\n#<VLA-OBJECT _Application 0017bb5c>")
           (url . "https://help.autodesk.com/cloudhelp/2023/ENU/AutoCAD-AutoLISP-Reference/files/GUID-7AFF597F-D630-4489-8349-94EF67CCE1F0.htm")
           (guid . "GUID-7AFF597F-D630-4489-8349-94EF67CCE1F0"))))
    *autolisp-reference-parts*))

(setq *autolisp-reference-entry* nil)

(setq *autolisp-reference-value* "GUID-B3F22E35-4666-452F-89C8-5BC15B9E9463")

(setq *autolisp-reference-entry* (cons (cons 'guid *autolisp-reference-value*) *autolisp-reference-entry*))

(setq *autolisp-reference-value* "https://help.autodesk.com/cloudhelp/2023/ENU/AutoCAD-AutoLISP-Reference/files/GUID-B3F22E35-4666-452F-89C8-5BC15B9E9463.htm")

(setq *autolisp-reference-entry* (cons (cons 'url *autolisp-reference-value*) *autolisp-reference-entry*))

(setq *autolisp-reference-value* "Begin by retrieving a pointer to the root AutoCAD object:\n\n(setq acadObject (vlax-get-acad-object))\n#<VLA-OBJECT IAcadApplication 00a4b2b4>\n\nGet the AutoCAD ActiveDocument property:\n\n(setq acadDocument (vlax-get-property acadObject 'ActiveDocument))\n#<VLA-OBJECT IAcadDocument 00302a18>\n\nThe function returns the current document object.\n\nGet the ModelSpace property of the ActiveDocument object:\n\n(setq mSpace (vlax-get-property acadDocument 'Modelspace))\n#<VLA-OBJECT IAcadModelSpace 00c14b44>\n\nThe model space object of the current document is returned.\n\nConvert a drawing entity to a VLA-object:\n\n(setq vlaobj (vlax-ename->vla-object e))\n#<VLA-OBJECT IAcadLWPolyline 0467114c>\n\nGet the color property of the object:\n\n(vlax-get-property vlaobj 'Color)\n256")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, List, VLA-object, Variant, Safearray, T, or nil\nThe value of the object's property.")

(setq *autolisp-reference-entry* (cons (cons 'return-values *autolisp-reference-value*) *autolisp-reference-entry*))

(setq *autolisp-reference-value* nil)

(setq *autolisp-reference-string* "Type: Symbol or String\nName of the property to be retrieved.")

(setq *autolisp-reference-value* (cons (cons "property" *autolisp-reference-string*) *autolisp-reference-value*))

(setq *autolisp-reference-string* "Type: VLA-object\nAn object.")

(setq *autolisp-reference-value* (cons (cons "object" *autolisp-reference-string*) *autolisp-reference-value*))

(setq *autolisp-reference-entry* (cons (cons 'arguments *autolisp-reference-value*) *autolisp-reference-entry*))

(setq *autolisp-reference-value* "(vlax-get-property object property)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Property-Handling Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Retrieves a VLA-object's property")

(setq *autolisp-reference-entry* (cons (cons 'summary *autolisp-reference-value*) *autolisp-reference-entry*))

(setq *autolisp-reference-value* "vlax-get-property (AutoLISP/ActiveX)")

(setq *autolisp-reference-entry* (cons (cons 'title *autolisp-reference-value*) *autolisp-reference-entry*))

(setq *autolisp-reference-value* "vlax-get-property")

(setq *autolisp-reference-entry* (cons (cons 'name *autolisp-reference-value*) *autolisp-reference-entry*))

(setq *autolisp-reference-parts* (cons (list (cons "vlax-get-property" *autolisp-reference-entry*)) *autolisp-reference-parts*))

(setq *autolisp-reference-entry* nil)

(setq *autolisp-reference-value* "GUID-1699B6A0-C4A6-4BC4-82DF-5040CFF3394A")

(setq *autolisp-reference-entry* (cons (cons 'guid *autolisp-reference-value*) *autolisp-reference-entry*))

(setq *autolisp-reference-value* "https://help.autodesk.com/cloudhelp/2023/ENU/AutoCAD-AutoLISP-Reference/files/GUID-1699B6A0-C4A6-4BC4-82DF-5040CFF3394A.htm")

(setq *autolisp-reference-entry* (cons (cons 'url *autolisp-reference-value*) *autolisp-reference-entry*))

(setq *autolisp-reference-value* "Import a Microsoft Word type library, assigning the prefix “msw-” to methods and properties, and “mswc-” to constants:\n\n(vlax-import-type-library\n  :tlb-filename \"C:/Program Files (x86)/Microsoft Office/root/Office16/msword.olb\"\n  :methods-prefix \"msw-\"\n  :properties-prefix \"msw-\"\n  :constants-prefix \"mswc-\")\nT")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nT, if successful; otherwise, nil if the library could not be imported.")

(setq *autolisp-reference-entry* (cons (cons 'return-values *autolisp-reference-value*) *autolisp-reference-entry*))

(setq *autolisp-reference-value* nil)

(setq *autolisp-reference-string* "Type: String\nPrefix to be used for constants contained in the type library. For example, if the type library contains a ccMaxCountOfRecords property with both read and write permissions, and cprefix is set to “cc-”, Visual LISP generates a constant named cc-ccMaxCountOfRecords. This parameter defaults to “”.")

(setq *autolisp-reference-value* (cons (cons "cprefix" *autolisp-reference-string*) *autolisp-reference-value*))

(setq *autolisp-reference-string* "Type: String\nPrefix to be used for property wrapper functions. For example, if the type library contains a Width property with both read and write permissions, and pprefix is set to “cc-”, then Visual LISP generates wrapper functions named cc-get-Width and cc-put-Width. This parameter defaults to “”.")

(setq *autolisp-reference-value* (cons (cons "pprefix" *autolisp-reference-string*) *autolisp-reference-value*))

(setq *autolisp-reference-string* "Type: String\nPrefix to be used for method wrapper functions. For example, if the type library contains a Calculate method and the mprefix parameter is set to “cc-”, Visual LISP generates a wrapper function named cc-Calculate. This parameter defaults to “”.")

(setq *autolisp-reference-value* (cons (cons "mprefix" *autolisp-reference-string*) *autolisp-reference-value*))

(setq *autolisp-reference-string* "Type: String\nName of the type library. A file can be one of the following types:\n- A type library (TLB) or object library (OLB) file\n- An executable (EXE) file\n- A library (DLL) file containing a type library resource\n- A compound document holding a type library\n- Any other file format that can be understood by the LoadTypeLib API\nIf you omit the path from tlb-filename, AutoCAD looks for the file in the support file search path.")

(setq *autolisp-reference-value* (cons (cons "filename" *autolisp-reference-string*) *autolisp-reference-value*))

(setq *autolisp-reference-entry* (cons (cons 'arguments *autolisp-reference-value*) *autolisp-reference-entry*))

(setq *autolisp-reference-value* "(vlax-import-type-library :tlb-filename filename [:methods-prefix mprefix  :properties-prefix pprefix :constants-prefix cprefix])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Drawing Object Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Imports information from a type library")

(setq *autolisp-reference-entry* (cons (cons 'summary *autolisp-reference-value*) *autolisp-reference-entry*))

(setq *autolisp-reference-value* "vlax-import-type-library (AutoLISP/ActiveX)")

(setq *autolisp-reference-entry* (cons (cons 'title *autolisp-reference-value*) *autolisp-reference-entry*))

(setq *autolisp-reference-value* "vlax-import-type-library")

(setq *autolisp-reference-entry* (cons (cons 'name *autolisp-reference-value*) *autolisp-reference-entry*))

(setq *autolisp-reference-parts* (cons (list (cons "vlax-import-type-library" *autolisp-reference-entry*)) *autolisp-reference-parts*))

(setq *autolisp-reference-entry* nil)

(setq *autolisp-reference-value* "GUID-A8B097A2-CE86-4B38-B2A9-D6F53EACA8ED")

(setq *autolisp-reference-entry* (cons (cons 'guid *autolisp-reference-value*) *autolisp-reference-entry*))

(setq *autolisp-reference-value* "https://help.autodesk.com/cloudhelp/2023/ENU/AutoCAD-AutoLISP-Reference/files/GUID-A8B097A2-CE86-4B38-B2A9-D6F53EACA8ED.htm")

(setq *autolisp-reference-entry* (cons (cons 'url *autolisp-reference-value*) *autolisp-reference-entry*))

(setq *autolisp-reference-value* "The following example uses the AddCircle method to draw a circle in the current AutoCAD drawing.\n\nThe first argument to AddCircle specifies the location of the center of the circle. The method requires the center to be specified as a variant containing a three-element array of doubles. You can use vlax-3d-point to convert an AutoLISP point list to the required variant data type:\n\n(setq circCenter (vlax-3d-point '(3.0 3.0 0.0)))\n#<variant 8197 ...>\n\nNow use vlax-invoke-method to draw a circle with the AddCircle method:\n\n(setq mycircle (vlax-invoke-method mspace 'AddCircle circCenter 3.0))\n#<VLA-OBJECT IAcadCircle 00bfd6e4>")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, List, VLA-object, Variant, Safearray, T, or nil\nDepends on the method invoked.")

(setq *autolisp-reference-entry* (cons (cons 'return-values *autolisp-reference-value*) *autolisp-reference-entry*))

(setq *autolisp-reference-value* nil)

(setq *autolisp-reference-string* "Type: Integer, Real, String, List, VLA-object, Variant, Safearray, T, or nil\nArgument to be passed to the method called. No argument type checking is performed.")

(setq *autolisp-reference-value* (cons (cons "arg" *autolisp-reference-string*) *autolisp-reference-value*))

(setq *autolisp-reference-string* "Type: Symbol or String\nA symbol or string naming the method to be called.")

(setq *autolisp-reference-value* (cons (cons "method" *autolisp-reference-string*) *autolisp-reference-value*))

(setq *autolisp-reference-string* "Type: VLA-object\nAn object.")

(setq *autolisp-reference-value* (cons (cons "obj" *autolisp-reference-string*) *autolisp-reference-value*))

(setq *autolisp-reference-entry* (cons (cons 'arguments *autolisp-reference-value*) *autolisp-reference-entry*))

(setq *autolisp-reference-value* "(vlax-invoke-method obj method arg [arg ...])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Method Invocation Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Calls the specified ActiveX method")

(setq *autolisp-reference-entry* (cons (cons 'summary *autolisp-reference-value*) *autolisp-reference-entry*))

(setq *autolisp-reference-value* "vlax-invoke-method (AutoLISP/ActiveX)")

(setq *autolisp-reference-entry* (cons (cons 'title *autolisp-reference-value*) *autolisp-reference-entry*))

(setq *autolisp-reference-value* "vlax-invoke-method")

(setq *autolisp-reference-entry* (cons (cons 'name *autolisp-reference-value*) *autolisp-reference-entry*))

(setq *autolisp-reference-parts* (cons (list (cons "vlax-invoke-method" *autolisp-reference-entry*)) *autolisp-reference-parts*))

(setq *autolisp-reference-parts*
  (cons
    '(("vlax-ldata-delete" .
          ((name . "vlax-ldata-delete")
           (title . "vlax-ldata-delete (AutoLISP/ActiveX)")
           (summary . "Erases LISP data from a drawing dictionary")
           (source-kind . "AutoLISP/ActiveX")
           (alphabetic-group . "V")
           (feature-groups . ("Dictionary Functions Reference (AutoLISP/ActiveX)" "Symbol Table and Dictionary-Handling"))
           (supported-platforms . "Windows only")
           (signature . "(vlax-ldata-delete dict key [private])")
           (arguments . (("dict" . "Type: VLA-object or String\nAn object, AutoCAD drawing entity object, or a string naming a global dictionary.")
                           ("key" . "Type: String\nDictionary key.")
                           ("private" . "Type: T or nil\nIf a non-nil value is specified for private and vlax-ldata-delete is called from a separate-namespace VLX, vlax-ldata-delete deletes private LISP data from dict.")))
           (return-values . "Type: T or nil\nT, if successful; otherwise nil (for example, the data did not exist).")
           (release-information . nil)
           (history . nil)
           (examples . "Add LISP data to a dictionary:\n\n(vlax-ldata-put \"dict\" \"key\" '(1))\n(1)\n\nUse vlax-ldata-delete to delete the LISP data:\n\n(vlax-ldata-delete \"dict\" \"key\")\nT\n\nIf vlax-ldata-delete is called again to remove the same data, it returns nil because the data does not exist in the dictionary:\n\n(vlax-ldata-delete \"dict\" \"key\")\nnil")
           (url . "https://help.autodesk.com/cloudhelp/2023/ENU/AutoCAD-AutoLISP-Reference/files/GUID-06F6C8B7-A55C-42DE-BD51-A9FAB68260D3.htm")
           (guid . "GUID-06F6C8B7-A55C-42DE-BD51-A9FAB68260D3"))))
    *autolisp-reference-parts*))

(setq *autolisp-reference-entry* nil)

(setq *autolisp-reference-value* "GUID-C279216F-9568-4176-A9E7-BCB45E3F59C7")

(setq *autolisp-reference-entry* (cons (cons 'guid *autolisp-reference-value*) *autolisp-reference-entry*))

(setq *autolisp-reference-value* "https://help.autodesk.com/cloudhelp/2023/ENU/AutoCAD-AutoLISP-Reference/files/GUID-C279216F-9568-4176-A9E7-BCB45E3F59C7.htm")

(setq *autolisp-reference-entry* (cons (cons 'url *autolisp-reference-value*) *autolisp-reference-entry*))

(setq *autolisp-reference-value* "(vlax-ldata-put \"mydict\" \"mykey\" \"Mumbo Dumbo\")\n\"Mumbo Dumbo\"\n\n(vlax-ldata-get \"mydict\" \"mykey\")\n\"Mumbo Dumbo\"")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, List, Ename (entity name), VLA-object, Variant, Safearray, T, or nil\nThe value of the key item.")

(setq *autolisp-reference-entry* (cons (cons 'return-values *autolisp-reference-value*) *autolisp-reference-entry*))

(setq *autolisp-reference-value* nil)

(setq *autolisp-reference-string* "Type: T or nil\nIf a non-nil value is specified for private and vlax-ldata-get is called from a separate-namespace VLX, vlax-ldata-get retrieves private LISP data from dict.\nIf you specify private, you must also specify default-data; you can use nil for default-data.")

(setq *autolisp-reference-value* (cons (cons "private" *autolisp-reference-string*) *autolisp-reference-value*))

(setq *autolisp-reference-string* "Type: Integer, Real, String, List, Ename (entity name), VLA-object, Variant, Safearray, T, or nil\nLISP data to be returned if no matching key exists in the dictionary.")

(setq *autolisp-reference-value* (cons (cons "default-data" *autolisp-reference-string*) *autolisp-reference-value*))

(setq *autolisp-reference-string* "Type: String\nDictionary key.")

(setq *autolisp-reference-value* (cons (cons "key" *autolisp-reference-string*) *autolisp-reference-value*))

(setq *autolisp-reference-string* "Type: VLA-object or String\nAn object, an AutoCAD drawing entity object, or a string naming a global dictionary.")

(setq *autolisp-reference-value* (cons (cons "dict" *autolisp-reference-string*) *autolisp-reference-value*))

(setq *autolisp-reference-entry* (cons (cons 'arguments *autolisp-reference-value*) *autolisp-reference-entry*))

(setq *autolisp-reference-value* "(vlax-ldata-get dict key [default-data [private]])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Dictionary Functions Reference (AutoLISP/ActiveX)" "Symbol Table and Dictionary-Handling"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Retrieves LISP data from a drawing dictionary or an object")

(setq *autolisp-reference-entry* (cons (cons 'summary *autolisp-reference-value*) *autolisp-reference-entry*))

(setq *autolisp-reference-value* "vlax-ldata-get (AutoLISP/ActiveX)")

(setq *autolisp-reference-entry* (cons (cons 'title *autolisp-reference-value*) *autolisp-reference-entry*))

(setq *autolisp-reference-value* "vlax-ldata-get")

(setq *autolisp-reference-entry* (cons (cons 'name *autolisp-reference-value*) *autolisp-reference-entry*))

(setq *autolisp-reference-parts* (cons (list (cons "vlax-ldata-get" *autolisp-reference-entry*)) *autolisp-reference-parts*))

(setq *autolisp-reference-parts*
  (cons
    '(("vlax-ldata-list" .
          ((name . "vlax-ldata-list")
           (title . "vlax-ldata-list (AutoLISP/ActiveX)")
           (summary . "Lists AutoLISP data in a drawing dictionary")
           (source-kind . "AutoLISP/ActiveX")
           (alphabetic-group . "V")
           (feature-groups . ("Dictionary Functions Reference (AutoLISP/ActiveX)" "Symbol Table and Dictionary-Handling"))
           (supported-platforms . "Windows only")
           (signature . "(vlax-ldata-list dict [private])")
           (arguments . (("dict" . "Type: VLA-object or String\nAn object, an AutoCAD drawing entity object, or a string naming a global dictionary.")
                           ("private" . "Type: T or nil\nIf vlax-ldata-list is called from a separate-namespace VLX and a non-nil value is specified for private, vlax-ldata-list retrieves only private data stored by the same VLX.")))
           (return-values . "Type: List\nAn associative list consisting of pairs (key . value).")
           (release-information . nil)
           (history . nil)
           (examples . "Use vlax-ldata-put to store LISP data in a dictionary:\n\n(vlax-ldata-put \"dict\" \"cay\" \"Mumbo Jumbo \")\n\"Mumbo Jumbo\"\n\n(vlax-ldata-put \"dict\" \"say\" \"Floobar \")\n\"Floobar\"\n\nUse vlax-ldata-list to display the LISP data stored in “dict”:\n\n (vlax-ldata-list \"dict\")\n((\"say\" . \"Floobar\") (\"cay\" . \"Mumbo Jumbo\"))")
           (url . "https://help.autodesk.com/cloudhelp/2023/ENU/AutoCAD-AutoLISP-Reference/files/GUID-A124867A-FBB8-4B36-9BB0-B50D971C91A1.htm")
           (guid . "GUID-A124867A-FBB8-4B36-9BB0-B50D971C91A1"))))
    *autolisp-reference-parts*))

(setq *autolisp-reference-parts*
  (cons
    '(("vlax-ldata-put" .
          ((name . "vlax-ldata-put")
           (title . "vlax-ldata-put (AutoLISP/ActiveX)")
           (summary . "Stores LISP data in a drawing dictionary or an object")
           (source-kind . "AutoLISP/ActiveX")
           (alphabetic-group . "V")
           (feature-groups . ("Dictionary Functions Reference (AutoLISP/ActiveX)" "Symbol Table and Dictionary-Handling"))
           (supported-platforms . "Windows only")
           (signature . "(vlax-ldata-put dict key data [private])")
           (arguments . (("dict" . "Type: VLA-object or String\nA object, an AutoCAD drawing entity object, or a string naming a global dictionary.")
                           ("key" . "Type: String\nDictionary key.")
                           ("data" . "Type: Integer, Real, String, List, Ename (entity name), VLA-object, Variant, Safearray, T, or nil\nLISP data to be stored in the dictionary.")
                           ("private" . "Type: T or nil\nIf vlax-ldata-put is called from a separate-namespace VLX and a non-nil value is specified for private, vlax-ldata-put marks the data as retrievable only by the same VLX.")))
           (return-values . "Type: Integer, Real, String, List, Ename (entity name), VLA-object, Variant, Safearray, T, or nil\nThe value of data.")
           (release-information . nil)
           (history . nil)
           (examples . "(vlax-ldata-put \"dict\" \"key\" '(1))\n(1)\n\n(vlax-ldata-put \"dict\" \"cay\" \"Gumbo jumbo\")\n\"Gumbo jumbo\"")
           (url . "https://help.autodesk.com/cloudhelp/2023/ENU/AutoCAD-AutoLISP-Reference/files/GUID-D2459C22-223C-4C8E-A69C-F288B8FBFA28.htm")
           (guid . "GUID-D2459C22-223C-4C8E-A69C-F288B8FBFA28"))))
    *autolisp-reference-parts*))

(setq *autolisp-reference-parts*
  (cons
    '(("vlax-ldata-test" .
          ((name . "vlax-ldata-test")
           (title . "vlax-ldata-test (AutoLISP/ActiveX)")
           (summary . "Determines if data can be saved over a session boundary")
           (source-kind . "AutoLISP/ActiveX")
           (alphabetic-group . "V")
           (feature-groups . ("Dictionary Functions Reference (AutoLISP/ActiveX)" "Symbol Table and Dictionary-Handling"))
           (supported-platforms . "Windows only")
           (signature . "(vlax-ldata-test data)")
           (arguments . (("data" . "Type: Integer, Real, String, List, Ename (entity name), VLA-object, Variant, Safearray, T, or nil\nAny LISP data to be tested.")))
           (return-values . "Type: T or nil\nT, if the data can be saved and restored over the session boundary; otherwise nil.")
           (release-information . nil)
           (history . nil)
           (examples . "Determine if a string can be saved as ldata over a session boundary:\n\n(vlax-ldata-test \"Gumbo jumbo\")\nT\n\nDetermine if a function can be saved as ldata over a session boundary:\n\n(vlax-ldata-test yinyang)\nnil")
           (url . "https://help.autodesk.com/cloudhelp/2023/ENU/AutoCAD-AutoLISP-Reference/files/GUID-CD72D160-25BF-43F5-BD30-AC715F4A2426.htm")
           (guid . "GUID-CD72D160-25BF-43F5-BD30-AC715F4A2426"))))
    *autolisp-reference-parts*))

(setq *autolisp-reference-parts*
  (cons
    '(("vlax-machine-product-key" .
          ((name . "vlax-machine-product-key")
           (title . "vlax-machine-product-key (AutoLISP/ActiveX)")
           (summary . "Returns the AutoCAD Windows registry path in the HKLM (HKEY_LOCAL_MACHINE)")
           (source-kind . "AutoLISP/ActiveX")
           (alphabetic-group . "V")
           (feature-groups . ("Windows Registry and Property List File"))
           (supported-platforms . "Windows only")
           (signature . "(vlax-machine-product-key)")
           (arguments . nil)
           (return-values . "Type: String\nA value containing the AutoCAD registry path.")
           (release-information . nil)
           (history . nil)
           (examples . "(vlax-machine-product-key)\n\"Software\\\\Autodesk\\\\AutoCAD\\\\R24.2\\\\ACAD-6101:409\"")
           (url . "https://help.autodesk.com/cloudhelp/2023/ENU/AutoCAD-AutoLISP-Reference/files/GUID-2EB68815-FDF9-4235-918B-025FB9A42220.htm")
           (guid . "GUID-2EB68815-FDF9-4235-918B-025FB9A42220"))))
    *autolisp-reference-parts*))

(setq *autolisp-reference-entry* nil)

(setq *autolisp-reference-value* "GUID-E0D40331-096B-4A52-A0D7-10204829C4A6")

(setq *autolisp-reference-entry* (cons (cons 'guid *autolisp-reference-value*) *autolisp-reference-entry*))

(setq *autolisp-reference-value* "https://help.autodesk.com/cloudhelp/2023/ENU/AutoCAD-AutoLISP-Reference/files/GUID-E0D40331-096B-4A52-A0D7-10204829C4A6.htm")

(setq *autolisp-reference-entry* (cons (cons 'url *autolisp-reference-value*) *autolisp-reference-entry*))

(setq *autolisp-reference-value* "Create a single-dimension safearray consisting of doubles, beginning with index 0:\n\n(setq point (vlax-make-safearray vlax-vbDouble '(0 . 3)))\n#<safearray...>\n\nUse the vlax-safearray->list function to display the contents of the safearray as a list:\n\n(vlax-safearray->list point)\n(0.0 0.0 0.0 0.0)\n\nThe result shows each element of the array was initialized to zero.\n\nCreate a two-dimension array of strings, with each dimension starting at index 1:\n\n(setq matrix (vlax-make-safearray vlax-vbString '(1 . 2) '(1 . 2) ))\n#<safearray...>")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Safearray\nThe safearray created.")

(setq *autolisp-reference-entry* (cons (cons 'return-values *autolisp-reference-value*) *autolisp-reference-entry*))

(setq *autolisp-reference-value* nil)

(setq *autolisp-reference-string* "Type: Integer\nLower and upper index boundaries of a dimension.")

(setq *autolisp-reference-value* (cons (cons "'(l-bound . u-bound)" *autolisp-reference-string*) *autolisp-reference-value*))

(setq *autolisp-reference-string* "Type: Integer\nThe type of safearray. Specify one of the following constants:\nvlax-vbInteger (2) -- Integer\nvlax-vbLong (3) -- Long integer\nvlax-vbSingle (4) -- Single-precision floating-point number\nvlax-vbDouble (5) -- Double-precision floating-point number\nvlax-vbString (8) -- String\nvlax-vbObject (9) -- Object\nvlax-vbBoolean (11) -- Boolean\nvlax-vbVariant (12) -- Variant\nThe integer shown in parentheses indicates the value to which the constant evaluates. It is recommended that you specify the constant in your argument, not the integer value, in case the value changes in later releases of AutoCAD.")

(setq *autolisp-reference-value* (cons (cons "type" *autolisp-reference-string*) *autolisp-reference-value*))

(setq *autolisp-reference-entry* (cons (cons 'arguments *autolisp-reference-value*) *autolisp-reference-entry*))

(setq *autolisp-reference-value* "(vlax-make-safearray type '(l-bound . u-bound) ['(l-bound . u-bound) ...)]")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Creates a safearray")

(setq *autolisp-reference-entry* (cons (cons 'summary *autolisp-reference-value*) *autolisp-reference-entry*))

(setq *autolisp-reference-value* "vlax-make-safearray (AutoLISP/ActiveX)")

(setq *autolisp-reference-entry* (cons (cons 'title *autolisp-reference-value*) *autolisp-reference-entry*))

(setq *autolisp-reference-value* "vlax-make-safearray")

(setq *autolisp-reference-entry* (cons (cons 'name *autolisp-reference-value*) *autolisp-reference-entry*))

(setq *autolisp-reference-parts* (cons (list (cons "vlax-make-safearray" *autolisp-reference-entry*)) *autolisp-reference-parts*))

(setq *autolisp-reference-entry* nil)

(setq *autolisp-reference-value* "GUID-A1B964E3-89B4-4655-9E37-B24401450CDA")

(setq *autolisp-reference-entry* (cons (cons 'guid *autolisp-reference-value*) *autolisp-reference-entry*))

(setq *autolisp-reference-value* "https://help.autodesk.com/cloudhelp/2023/ENU/AutoCAD-AutoLISP-Reference/files/GUID-A1B964E3-89B4-4655-9E37-B24401450CDA.htm")

(setq *autolisp-reference-entry* (cons (cons 'url *autolisp-reference-value*) *autolisp-reference-entry*))

(setq *autolisp-reference-value* "Create a variant using the defaults for vlax-make-variant:\n\n(setq varnil (vlax-make-variant))\n#<variant 0 >\n\nThe function creates an uninitialized (vlax-vbEmpty) variant by default. You can accomplish the same thing explicitly with the following call:\n\n(setq varnil (vlax-make-variant nil))\n#<variant 0 >\n\nCreate an integer variant and set its value to 5:\n\n(setq varint (vlax-make-variant 5 vlax-vbInteger))\n#<variant 2 5>\n\nRepeat the previous command, but omit the type argument and see what happens:\n\n(setq varint (vlax-make-variant 5))\n#<variant 3 5>\n\nBy default, vlax-make-variant assigned the specified integer value to a Long integer data type, not Integer, as you might expect. This highlights the importance of explicitly stating the type of variant you want when working with numbers.\n\nOmitting the type argument for a string produces predictable results:\n\n(setq vars")

(setq *autolisp-reference-value* (strcat *autolisp-reference-value* "tr (vlax-make-variant \"ghost\"))\n#<variant 8 ghost>\n\nTo create a variant containing arrays, you must specify type vlax-vbArray, along with the type of data in the array. For example, to create a variant containing an array of doubles, first set a variable's value to an array of doubles:\n\n(setq 4dubs (vlax-make-safearray vlax-vbDouble '(0 . 3)))\n#<safearray...>\n\nThen take the array of doubles and assign it to a variant:\n\n(vlax-make-variant 4dubs)\n#<variant 8197 ...>"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: variant\nThe variant created.")

(setq *autolisp-reference-entry* (cons (cons 'return-values *autolisp-reference-value*) *autolisp-reference-entry*))

(setq *autolisp-reference-value* nil)

(setq *autolisp-reference-string* "Type: Integer\nThe type of variant. This can be represented by one of the following constants:\nvlax-vbEmpty (0) -- Uninitialized (default value)\nvlax-vbNull (1) -- Contains no valid data\nvlax-vbInteger (2) -- Integer\nvlax-vbLong (3) -- Long integer\nvlax-vbSingle (4) -- Single-precision floating-point number\nvlax-vbDouble (5) -- Double-precision floating-point number\nvlax-vbString (8) -- String\nvlax-vbObject (9) -- Object\nvlax-vbBoolean (11) -- Boolean\nvlax-vbArray (8192) -- Array\nThe integer shown in parentheses indicates the value to which the constant evaluates. It is recommended that you specify the constant in your argument, not the integer value, because the value may change in later releases of AutoCAD.\nIf you do not specify a type, vlax-make-variant assigns a default data type based on the data type of the value it receives. The following list identifies the default va")

(setq *autolisp-reference-string* (strcat *autolisp-reference-string* "riant data type assigned to each LISP data type:\nnil -- vlax-vbEmpty\n:vlax-null -- vlax-vbNull\ninteger -- vlax-vbLong\nreal -- vlax-vbDouble\nstring -- vlax-vbString\nVLA-object -- vlax-vbObject\n:vlax-true/:vlax-false -- vlax-vbBoolean\nvariant -- Same as the type of initial value\nvlax-make-safearray -- vlax-vbArray"))

(setq *autolisp-reference-value* (cons (cons "type" *autolisp-reference-string*) *autolisp-reference-value*))

(setq *autolisp-reference-string* "Type: Integer, Real, String, VLA-object, Safearray, T, or nil\nThe value to be assigned to the variant. If omitted, the variant is created with the vlax-vbEmpty type (uninitialized).")

(setq *autolisp-reference-value* (cons (cons "value" *autolisp-reference-string*) *autolisp-reference-value*))

(setq *autolisp-reference-entry* (cons (cons 'arguments *autolisp-reference-value*) *autolisp-reference-entry*))

(setq *autolisp-reference-value* "(vlax-make-variant [value [type]])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Creates a variant data type")

(setq *autolisp-reference-entry* (cons (cons 'summary *autolisp-reference-value*) *autolisp-reference-entry*))

(setq *autolisp-reference-value* "vlax-make-variant (AutoLISP/ActiveX)")

(setq *autolisp-reference-entry* (cons (cons 'title *autolisp-reference-value*) *autolisp-reference-entry*))

(setq *autolisp-reference-value* "vlax-make-variant")

(setq *autolisp-reference-entry* (cons (cons 'name *autolisp-reference-value*) *autolisp-reference-entry*))

(setq *autolisp-reference-parts* (cons (list (cons "vlax-make-variant" *autolisp-reference-entry*)) *autolisp-reference-parts*))

(setq *autolisp-reference-entry* nil)

(setq *autolisp-reference-value* "GUID-81247560-E2A7-486E-ABCD-B85E09266FBA")

(setq *autolisp-reference-entry* (cons (cons 'guid *autolisp-reference-value*) *autolisp-reference-entry*))

(setq *autolisp-reference-value* "https://help.autodesk.com/cloudhelp/2023/ENU/AutoCAD-AutoLISP-Reference/files/GUID-81247560-E2A7-486E-ABCD-B85E09266FBA.htm")

(setq *autolisp-reference-entry* (cons (cons 'url *autolisp-reference-value*) *autolisp-reference-entry*))

(setq *autolisp-reference-value* "(vlax-map-collection (vla-get-ModelSpace acadDocument) 'vlax-dump-object)\n; IAcadLWPolyline: AutoCAD Lightweight Polyline Interface\n; Property values:\n;   Application (RO) = #<VLA-OBJECT IAcadApplication 00a4ae24>\n;   Area (RO) = 2.46556\n;   Closed = 0\n;   Color = 256\n;   ConstantWidth = 0.0\n;   Coordinate = ...Indexed contents not shown...\n;   Coordinates = (8.49917 7.00155 11.2996 3.73137 14.8 5.74379 ... )\n;   Database (RO) = #<VLA-OBJECT IAcadDatabase 01e3da44>\n;   Elevation = 0.0\n;   Handle (RO) = \"53\"\n;   HasExtensionDictionary (RO) = 0\n;   Hyperlinks (RO) = #<VLA-OBJECT IAcadHyperlinks 01e3d7d4>\n;   Layer = \"0\"\n;   Linetype = \"BYLAYER\"\n;   LinetypeGeneration = 0\n;   LinetypeScale = 1.0\n;   Lineweight = -1\n;   Normal = (0.0 0.0 1.0)\n;   ObjectID (RO) = 28895576\n;   ObjectName (RO) = \"AcDbPolyline\"\n;   PlotStyleName = \"ByLayer\"\n;   Thickness = 0.0\n")

(setq *autolisp-reference-value* (strcat *autolisp-reference-value* ";   Visible = -1\nT"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, VLA-object, Variant, Safearray, T, or nil\nThe obj first argument.")

(setq *autolisp-reference-entry* (cons (cons 'return-values *autolisp-reference-value*) *autolisp-reference-entry*))

(setq *autolisp-reference-value* nil)

(setq *autolisp-reference-string* "Type: Subroutine or Symbol\nA symbol or lambda expression to be applied to obj.")

(setq *autolisp-reference-value* (cons (cons "function" *autolisp-reference-string*) *autolisp-reference-value*))

(setq *autolisp-reference-string* "Type: VLA-object\nAn object representing a collection.")

(setq *autolisp-reference-value* (cons (cons "obj" *autolisp-reference-string*) *autolisp-reference-value*))

(setq *autolisp-reference-entry* (cons (cons 'arguments *autolisp-reference-value*) *autolisp-reference-entry*))

(setq *autolisp-reference-value* "(vlax-map-collection obj function)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Collection Manipulation Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Applies a function to all objects in a collection")

(setq *autolisp-reference-entry* (cons (cons 'summary *autolisp-reference-value*) *autolisp-reference-entry*))

(setq *autolisp-reference-value* "vlax-map-collection (AutoLISP/ActiveX)")

(setq *autolisp-reference-entry* (cons (cons 'title *autolisp-reference-value*) *autolisp-reference-entry*))

(setq *autolisp-reference-value* "vlax-map-collection")

(setq *autolisp-reference-entry* (cons (cons 'name *autolisp-reference-value*) *autolisp-reference-entry*))

(setq *autolisp-reference-parts* (cons (list (cons "vlax-map-collection" *autolisp-reference-entry*)) *autolisp-reference-parts*))

(setq *autolisp-reference-parts*
  (cons
    '(("vlax-method-applicable-p" .
          ((name . "vlax-method-applicable-p")
           (title . "vlax-method-applicable-p (AutoLISP/ActiveX)")
           (summary . "Determines if an object supports a particular method")
           (source-kind . "AutoLISP/ActiveX")
           (alphabetic-group . "V")
           (feature-groups . ("Drawing Object Functions Reference (AutoLISP/ActiveX)" "Method Invocation Functions Reference (AutoLISP/ActiveX)" "Object-Handling" "Object-Handling Functions Reference (AutoLISP/ActiveX)"))
           (supported-platforms . "Windows only")
           (signature . "(vlax-method-applicable-p obj method)")
           (arguments . (("obj" . "Type: VLA-object\nAn object.")
                           ("method" . "Type: Symbol or String\nA symbol or string containing the name of the method to be checked.")))
           (return-values . "Type: T or nil\nT, if the object supports the method; otherwise nil.")
           (release-information . nil)
           (history . nil)
           (examples . "The following commands are issued against a LightweightPolyline object:\n\n(vlax-method-applicable-p WhatsMyLine 'copy)\nT\n\n(vlax-method-applicable-p WhatsMyLine 'AddBox)\nnil")
           (url . "https://help.autodesk.com/cloudhelp/2023/ENU/AutoCAD-AutoLISP-Reference/files/GUID-63B81424-11BA-4CB3-A783-514031A2271D.htm")
           (guid . "GUID-63B81424-11BA-4CB3-A783-514031A2271D"))))
    *autolisp-reference-parts*))

(setq *autolisp-reference-parts*
  (cons
    '(("vlax-object-released-p" .
          ((name . "vlax-object-released-p")
           (title . "vlax-object-released-p (AutoLISP/ActiveX)")
           (summary . "Determines if an object has been released")
           (source-kind . "AutoLISP/ActiveX")
           (alphabetic-group . "V")
           (feature-groups . ("Drawing Object Functions Reference (AutoLISP/ActiveX)" "Object-Handling" "Object-Handling Functions Reference (AutoLISP/ActiveX)"))
           (supported-platforms . "Windows only")
           (signature . "(vlax-object-released-p obj)")
           (arguments . (("obj" . "Type: VLA-object\nAn object.")))
           (return-values . "Type: T or nil\nT, if the object is released (no AutoCAD drawing object is attached to obj); nil if the object has not been released.")
           (release-information . nil)
           (history . nil)
           (examples . "Attach a Microsoft Excel application to the current AutoCAD drawing:\n\n(setq excelobj (vlax-get-object \"Excel.Application\"))\n#<VLA-OBJECT _Application 00168a54>\n\nRelease the Excel object:\n\n(vlax-release-object excelobj)\n1\n\nIssue vlax-object-released-p to verify the object was released:\n\n(vlax-object-released-p excelobj)\nT")
           (url . "https://help.autodesk.com/cloudhelp/2023/ENU/AutoCAD-AutoLISP-Reference/files/GUID-23DA7B30-FBB5-40DC-A93E-E1FC2A5D8B6F.htm")
           (guid . "GUID-23DA7B30-FBB5-40DC-A93E-E1FC2A5D8B6F"))))
    *autolisp-reference-parts*))

(setq *autolisp-reference-parts*
  (cons
    '(("vlax-product-key" .
          ((name . "vlax-product-key")
           (title . "vlax-product-key (AutoLISP/ActiveX)")
           (summary . "Returns the AutoCAD Windows registry path")
           (source-kind . "AutoLISP/ActiveX")
           (alphabetic-group . "V")
           (feature-groups . ("Windows Registry and Property List File"))
           (supported-platforms . "Windows only")
           (signature . "(vlax-product-key)")
           (arguments . nil)
           (return-values . "Type: String\nA value containing the AutoCAD registry path.")
           (release-information . nil)
           (history . nil)
           (examples . "(vlax-product-key)\n\"Software\\\\Autodesk\\\\AutoCAD\\\\R24.2\\\\ACAD-6101:409\"")
           (url . "https://help.autodesk.com/cloudhelp/2023/ENU/AutoCAD-AutoLISP-Reference/files/GUID-237CEDFA-A02E-443E-BB21-5BD86E5E353E.htm")
           (guid . "GUID-237CEDFA-A02E-443E-BB21-5BD86E5E353E"))))
    *autolisp-reference-parts*))

(setq *autolisp-reference-entry* nil)

(setq *autolisp-reference-value* "GUID-E8A5B009-46D6-4BA7-9655-88104F8BE792")

(setq *autolisp-reference-entry* (cons (cons 'guid *autolisp-reference-value*) *autolisp-reference-entry*))

(setq *autolisp-reference-value* "https://help.autodesk.com/cloudhelp/2023/ENU/AutoCAD-AutoLISP-Reference/files/GUID-E8A5B009-46D6-4BA7-9655-88104F8BE792.htm")

(setq *autolisp-reference-entry* (cons (cons 'url *autolisp-reference-value*) *autolisp-reference-entry*))

(setq *autolisp-reference-value* "The following examples apply to a LightweightPolyline object:\n\n(vlax-property-available-p WhatsMyLine 'Color)\nT\n\n(vlax-property-available-p WhatsMyLine 'center)\nnil\n\nThe following examples apply to a Circle object:\n\n(vlax-property-available-p myCircle 'area)\nT\n\nNote how supplying the optional third argument changes the result:\n\n(vlax-property-available-p myCircle 'area T)\nnil\n\nThe function returns nil because, although the circle has an “area” property, that property cannot be modified.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: T or nil\nT, if the object has the specified property; otherwise nil. If T is specified for the check-modify argument, vlax-property-available-p returns nil if either the property is not available or the property cannot be modified.")

(setq *autolisp-reference-entry* (cons (cons 'return-values *autolisp-reference-value*) *autolisp-reference-entry*))

(setq *autolisp-reference-value* nil)

(setq *autolisp-reference-string* "Type: T\nIf T is specified for this argument, vlax-property-available-p also checks that the property can be modified.")

(setq *autolisp-reference-value* (cons (cons "check-modify" *autolisp-reference-string*) *autolisp-reference-value*))

(setq *autolisp-reference-string* "Type: Symbol or String\nName of the property to be checked.")

(setq *autolisp-reference-value* (cons (cons "property" *autolisp-reference-string*) *autolisp-reference-value*))

(setq *autolisp-reference-string* "Type: VLA-object\nAn object.")

(setq *autolisp-reference-value* (cons (cons "obj" *autolisp-reference-string*) *autolisp-reference-value*))

(setq *autolisp-reference-entry* (cons (cons 'arguments *autolisp-reference-value*) *autolisp-reference-entry*))

(setq *autolisp-reference-value* "(vlax-property-available-p obj prop [check-modify])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Property-Handling Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Determines if an object has a specified property")

(setq *autolisp-reference-entry* (cons (cons 'summary *autolisp-reference-value*) *autolisp-reference-entry*))

(setq *autolisp-reference-value* "vlax-property-available-p (AutoLISP/ActiveX)")

(setq *autolisp-reference-entry* (cons (cons 'title *autolisp-reference-value*) *autolisp-reference-entry*))

(setq *autolisp-reference-value* "vlax-property-available-p")

(setq *autolisp-reference-entry* (cons (cons 'name *autolisp-reference-value*) *autolisp-reference-entry*))

(setq *autolisp-reference-parts* (cons (list (cons "vlax-property-available-p" *autolisp-reference-entry*)) *autolisp-reference-parts*))

(setq *autolisp-reference-parts*
  (cons
    '(("vlax-put-property" .
          ((name . "vlax-put-property")
           (title . "vlax-put-property (AutoLISP/ActiveX)")
           (summary . "Sets the property of an ActiveX object")
           (source-kind . "AutoLISP/ActiveX")
           (alphabetic-group . "V")
           (feature-groups . ("Property-Handling Functions Reference (AutoLISP/ActiveX)"))
           (supported-platforms . "Windows only")
           (signature . "(vlax-put-property obj property arg)")
           (arguments . (("obj" . "Type: VLA-object\nAn object.")
                           ("property" . "Type: Symbol or String\nName of the property to be set.")
                           ("arg" . "Type: Integer, Real, String, VLA-object, Safearray, Variant, T, or nil\nThe value to be set.")))
           (return-values . "Type: nil or error\nnil, if successful; otherwise, an error occurs.")
           (release-information . nil)
           (history . nil)
           (examples . "Color an object red:\n\n(vlax-put-property vlaobj 'Color 1)\nnil")
           (url . "https://help.autodesk.com/cloudhelp/2023/ENU/AutoCAD-AutoLISP-Reference/files/GUID-C56E4AF5-A763-4B9D-AB35-C863D02FB93B.htm")
           (guid . "GUID-C56E4AF5-A763-4B9D-AB35-C863D02FB93B"))))
    *autolisp-reference-parts*))

(setq *autolisp-reference-parts*
  (cons
    '(("vlax-read-enabled-p" .
          ((name . "vlax-read-enabled-p")
           (title . "vlax-read-enabled-p (AutoLISP/ActiveX)")
           (summary . "Determines if an object can be read")
           (source-kind . "AutoLISP/ActiveX")
           (alphabetic-group . "V")
           (feature-groups . ("Drawing Object Functions Reference (AutoLISP/ActiveX)" "Object-Handling" "Object-Handling Functions Reference (AutoLISP/ActiveX)"))
           (supported-platforms . "Windows only")
           (signature . "(vlax-read-enabled-p obj)")
           (arguments . (("obj" . "Type: VLA-object\nAn object.")))
           (return-values . "Type: T or nil\nT, if the object is readable; otherwise nil.")
           (release-information . nil)
           (history . nil)
           (examples . "N/A")
           (url . "https://help.autodesk.com/cloudhelp/2023/ENU/AutoCAD-AutoLISP-Reference/files/GUID-8BBBF683-BA93-4942-9B8C-AD43D490E52A.htm")
           (guid . "GUID-8BBBF683-BA93-4942-9B8C-AD43D490E52A"))))
    *autolisp-reference-parts*))

(setq *autolisp-reference-parts*
  (cons
    '(("vlax-release-object" .
          ((name . "vlax-release-object")
           (title . "vlax-release-object (AutoLISP/ActiveX)")
           (summary . "Releases a drawing object")
           (source-kind . "AutoLISP/ActiveX")
           (alphabetic-group . "V")
           (feature-groups . ("Drawing Object Functions Reference (AutoLISP/ActiveX)" "Object-Handling" "Object-Handling Functions Reference (AutoLISP/ActiveX)"))
           (supported-platforms . "Windows only")
           (signature . "(vlax-release-object obj)")
           (arguments . (("obj" . "Type: VLA-object\nAn object.")))
           (return-values . "Type: Integer or error\nA numeric value if the object is successfully released; otherwise, an error occurs if the object is already released.")
           (release-information . nil)
           (history . nil)
           (examples . "N/A")
           (url . "https://help.autodesk.com/cloudhelp/2023/ENU/AutoCAD-AutoLISP-Reference/files/GUID-85FA59E7-9EC9-4690-8CEE-318BF542C0E6.htm")
           (guid . "GUID-85FA59E7-9EC9-4690-8CEE-318BF542C0E6"))))
    *autolisp-reference-parts*))

(setq *autolisp-reference-parts*
  (cons
    '(("vlax-remove-cmd" .
          ((name . "vlax-remove-cmd")
           (title . "vlax-remove-cmd (AutoLISP/ActiveX)")
           (summary . "Removes a single command or a command group")
           (source-kind . "AutoLISP/ActiveX")
           (alphabetic-group . "V")
           (feature-groups . ("Query and Command"))
           (supported-platforms . "Windows only")
           (signature . "(vlax-remove-cmd global-name)")
           (arguments . (("global-name" . "Type: String or T\nName of the command, or T. If global-name is T, the whole command group VLC-AppName (for example, VLC-VLIDE) is deleted.")))
           (return-values . "Type: T or nil\nT, if successful; otherwise nil (for example, the command is not defined).")
           (release-information . nil)
           (history . nil)
           (examples . "Remove a command defined with vlax-add-cmd:\n\n(vlax-remove-cmd \"hello-autocad\")\nT\n\nRepeat the vlax-remove-cmd:\n\n(vlax-remove-cmd \"hello-autocad\")\nnil\n\nThis time vlax-remove-cmd returns nil, because the specified command does not exist anymore.")
           (url . "https://help.autodesk.com/cloudhelp/2023/ENU/AutoCAD-AutoLISP-Reference/files/GUID-EA671EF1-4EF9-49FE-9166-E241657198A1.htm")
           (guid . "GUID-EA671EF1-4EF9-49FE-9166-E241657198A1"))))
    *autolisp-reference-parts*))

(setq *autolisp-reference-parts*
  (cons
    '(("vlax-safearray->list" .
          ((name . "vlax-safearray->list")
           (title . "vlax-safearray->list (AutoLISP/ActiveX)")
           (summary . "Returns the elements of a safearray in list form")
           (source-kind . "AutoLISP/ActiveX")
           (alphabetic-group . "V")
           (feature-groups . ("Data Conversion Functions Reference (AutoLISP/ActiveX)"))
           (supported-platforms . "Windows only")
           (signature . "(vlax-safearray->list var)")
           (arguments . (("var" . "Type: Safearray\nA variable containing a safearray.")))
           (return-values . "Type: List or nil\nA list containing the elements of the safearray.")
           (release-information . nil)
           (history . nil)
           (examples . "Create a single-dimension array of doubles:\n\n(setq point (vlax-make-safearray vlax-vbDouble '(0 . 2)))\n#<safearray...>\n\nUse vlax-safearray-put-element to populate the array:\n\n(vlax-safearray-put-element point 0 100)\n100\n\n(vlax-safearray-put-element point 1 100)\n100\n\n(vlax-safearray-put-element point 2 0)\n0\n\nConvert the array to a list:\n\n(setq pointlist (vlax-safearray->list point))\n(100.0 100.0 0.0)\n\nThe following example demonstrates how a two-dimension array of strings is displayed by vlax-safearray->list:\n\n(vlax-safearray->list matrix)\n((\"a\" \"b\") (\"c\" \"d\"))")
           (url . "https://help.autodesk.com/cloudhelp/2023/ENU/AutoCAD-AutoLISP-Reference/files/GUID-A38DDA9E-1E84-4529-9744-4C07219A28DB.htm")
           (guid . "GUID-A38DDA9E-1E84-4529-9744-4C07219A28DB"))))
    *autolisp-reference-parts*))

(setq *autolisp-reference-entry* nil)

(setq *autolisp-reference-value* "GUID-7C2331B4-1A4D-40FF-B59A-D35F7942936B")

(setq *autolisp-reference-entry* (cons (cons 'guid *autolisp-reference-value*) *autolisp-reference-entry*))

(setq *autolisp-reference-value* "https://help.autodesk.com/cloudhelp/2023/ENU/AutoCAD-AutoLISP-Reference/files/GUID-7C2331B4-1A4D-40FF-B59A-D35F7942936B.htm")

(setq *autolisp-reference-entry* (cons (cons 'url *autolisp-reference-value*) *autolisp-reference-entry*))

(setq *autolisp-reference-value* "Create a single-dimension array of doubles:\n\n(setq sa (vlax-make-safearray vlax-vbdouble '(0 . 2)))\n#<safearray...>\n\nUse vlax-safearray-fill to populate the array:\n\n(vlax-safearray-fill sa '(1 2 3))\n#<safearray...>\n\nList the contents of the array:\n\n(vlax-safearray->list sa)\n(1.0 2.0 3.0)\n\nUse vlax-safearray-fill to set the first element in the array:\n\n(vlax-safearray-fill sa '(-66))\n#<safearray...>\n\nList the contents of the array:\n\n(vlax-safearray->list sa)\n(-66.0 2.0 3.0)\n\nNotice that only the first element in the array has been changed; the remaining elements are unaffected and retain the value you previously set them to. If you need to change the second or third element and leave the first element unaffected, use vlax-put-element.\n\nInstruct vlax-safearray-fill to set four elements in an array that contains only three elements:\n\n(vlax-safearray-fill sa '(1 ")

(setq *autolisp-reference-value* (strcat *autolisp-reference-value* "2 3 4))\nError: Assertion failed: safearray-fill failed. Too many elements.\n\nThe vlax-safearray-fill function returns an error if you specify more elements than the array contains.\n\nTo assign values to a multi-dimensional array, specify a list of lists to vlax-safearray-fill, with each list corresponding to a dimension. The following command creates a two-dimension array of strings containing three elements in each dimension:\n\n(setq mat2 (vlax-make-safearray vlax-vbString '(0 . 1) '(1 . 3)))\n#<safearray...>\n\nUse vlax-safearray-fill to populate the array:\n\n(vlax-safearray-fill mat2 '((\"a\" \"b\" \"c\") (\"d\" \"e\" \"f\")))\n#<safearray...>\n\nCall the vlax-safearray->list function to confirm the contents of mat2:\n\n(vlax-safearray->list mat2)\n((\"a\" \"b\" \"c\") (\"d\" \"e\" \"f\"))"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List or nil\nValue provided in the var argument.")

(setq *autolisp-reference-entry* (cons (cons 'return-values *autolisp-reference-value*) *autolisp-reference-entry*))

(setq *autolisp-reference-value* nil)

(setq *autolisp-reference-string* "Type: List\nValues to be stored in the array. You can specify as many values as there are elements in the array. If you specify fewer values than there are elements, the remaining elements retain their current value.\nFor multi-dimension arrays, element-values must be a list of lists, with each list corresponding to a dimension of the array.")

(setq *autolisp-reference-value* (cons (cons "'element-values" *autolisp-reference-string*) *autolisp-reference-value*))

(setq *autolisp-reference-string* "Type: Safearray\nA variable containing a safearray.")

(setq *autolisp-reference-value* (cons (cons "var" *autolisp-reference-string*) *autolisp-reference-value*))

(setq *autolisp-reference-entry* (cons (cons 'arguments *autolisp-reference-value*) *autolisp-reference-entry*))

(setq *autolisp-reference-value* "(vlax-safearray-fill var 'element-values)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Stores data in the elements of a safearray")

(setq *autolisp-reference-entry* (cons (cons 'summary *autolisp-reference-value*) *autolisp-reference-entry*))

(setq *autolisp-reference-value* "vlax-safearray-fill (AutoLISP/ActiveX)")

(setq *autolisp-reference-entry* (cons (cons 'title *autolisp-reference-value*) *autolisp-reference-entry*))

(setq *autolisp-reference-value* "vlax-safearray-fill")

(setq *autolisp-reference-entry* (cons (cons 'name *autolisp-reference-value*) *autolisp-reference-entry*))

(setq *autolisp-reference-parts* (cons (list (cons "vlax-safearray-fill" *autolisp-reference-entry*)) *autolisp-reference-parts*))

(setq *autolisp-reference-parts*
  (cons
    '(("vlax-safearray-get-dim" .
          ((name . "vlax-safearray-get-dim")
           (title . "vlax-safearray-get-dim (AutoLISP/ActiveX)")
           (summary . "Returns the number of dimensions in a safearray object")
           (source-kind . "AutoLISP/ActiveX")
           (alphabetic-group . "V")
           (feature-groups . ("Data Conversion Functions Reference (AutoLISP/ActiveX)"))
           (supported-platforms . "Windows only")
           (signature . "(vlax-safearray-get-dim var)")
           (arguments . (("var" . "Type: Safearray\nA variable containing a safearray.")))
           (return-values . "Type: Integer or nil\nA numeric value identifying the number of dimensions in var. An error occurs if var is not a safearray.")
           (release-information . nil)
           (history . nil)
           (examples . "Set sa-int to a single-dimension safearray with one dimension:\n\n(setq sa-int (vlax-make-safearray vlax-vbinteger '(1 . 4)))\n#<safearray...>\n\nUse vlax-safearray-get-dim to return the number of dimensions in sa-int:\n\n(vlax-safearray-get-dim sa-int)\n1")
           (url . "https://help.autodesk.com/cloudhelp/2023/ENU/AutoCAD-AutoLISP-Reference/files/GUID-FA24BF36-D548-44E2-B945-76445CE7BEB7.htm")
           (guid . "GUID-FA24BF36-D548-44E2-B945-76445CE7BEB7"))))
    *autolisp-reference-parts*))

(setq *autolisp-reference-entry* nil)

(setq *autolisp-reference-value* "GUID-09386E77-DBBF-4E4D-8D77-0066D1F11CBA")

(setq *autolisp-reference-entry* (cons (cons 'guid *autolisp-reference-value*) *autolisp-reference-entry*))

(setq *autolisp-reference-value* "https://help.autodesk.com/cloudhelp/2023/ENU/AutoCAD-AutoLISP-Reference/files/GUID-09386E77-DBBF-4E4D-8D77-0066D1F11CBA.htm")

(setq *autolisp-reference-entry* (cons (cons 'url *autolisp-reference-value*) *autolisp-reference-entry*))

(setq *autolisp-reference-value* "Create an array with two dimensions, each dimension starting at index 1:\n\n(setq matrix (vlax-make-safearray vlax-vbString '(1 . 2) '(1 . 2) ))\n#<safearray...>\n\nUse vlax-safearray-put-element to populate the array:\n\n(vlax-safearray-put-element matrix 1 1 \"a\")\n\"a\"\n\n(vlax-safearray-put-element matrix 1 2 \"b\")\n\"b\"\n\n(vlax-safearray-put-element matrix 2 1 \"c\")\n\"c\"\n\n(vlax-safearray-put-element matrix 2 2 \"d\")\n\"d\"\n\nUse vlax-safearray-get-element to retrieve the second element in the first dimension of the array:\n\n(vlax-safearray-get-element matrix 1 2)\n\"b\"")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, VLA-object, Safearray, Variant, T, or nil\nThe value of the element.")

(setq *autolisp-reference-entry* (cons (cons 'return-values *autolisp-reference-value*) *autolisp-reference-entry*))

(setq *autolisp-reference-value* nil)

(setq *autolisp-reference-string* "Type: Integer\nNumeric values specifying the indexes of the element to be retrieved. For an array with one dimension, specify a single integer. For multi-dimension arrays, specify as many indexes as there are dimensions.")

(setq *autolisp-reference-value* (cons (cons "element ..." *autolisp-reference-string*) *autolisp-reference-value*))

(setq *autolisp-reference-string* "Type: Safearray\nA variable containing a safearray.")

(setq *autolisp-reference-value* (cons (cons "var" *autolisp-reference-string*) *autolisp-reference-value*))

(setq *autolisp-reference-entry* (cons (cons 'arguments *autolisp-reference-value*) *autolisp-reference-entry*))

(setq *autolisp-reference-value* "(vlax-safearray-get-element var element ...)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns an element from an array")

(setq *autolisp-reference-entry* (cons (cons 'summary *autolisp-reference-value*) *autolisp-reference-entry*))

(setq *autolisp-reference-value* "vlax-safearray-get-element (AutoLISP/ActiveX)")

(setq *autolisp-reference-entry* (cons (cons 'title *autolisp-reference-value*) *autolisp-reference-entry*))

(setq *autolisp-reference-value* "vlax-safearray-get-element")

(setq *autolisp-reference-entry* (cons (cons 'name *autolisp-reference-value*) *autolisp-reference-entry*))

(setq *autolisp-reference-parts* (cons (list (cons "vlax-safearray-get-element" *autolisp-reference-entry*)) *autolisp-reference-parts*))

(setq *autolisp-reference-entry* nil)

(setq *autolisp-reference-value* "GUID-8ABBA8A8-D421-48D2-BCBC-34DA1C728A78")

(setq *autolisp-reference-entry* (cons (cons 'guid *autolisp-reference-value*) *autolisp-reference-entry*))

(setq *autolisp-reference-value* "https://help.autodesk.com/cloudhelp/2023/ENU/AutoCAD-AutoLISP-Reference/files/GUID-8ABBA8A8-D421-48D2-BCBC-34DA1C728A78.htm")

(setq *autolisp-reference-entry* (cons (cons 'url *autolisp-reference-value*) *autolisp-reference-entry*))

(setq *autolisp-reference-value* "The following examples evaluate a safearray defined as follows:\n\n(vlax-make-safearray vlax-vbString '(1 . 2) '(0 . 1) ))\n\nGet the starting index value of the array's first dimension:\n\n(vlax-safearray-get-l-bound tmatrix 1)\n1\n\nThe first dimension starts with index 1.\n\nGet the starting index value of the second dimension of the array:\n\n(vlax-safearray-get-l-bound tmatrix 2)\n0\n\nThe second dimension starts with index 0.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer\nA numeric value representing the lower boundary (starting index) of the dimension. If var is not an array, or dim is invalid (for example, 0, or a number greater than the number of dimensions in the array), an error results.")

(setq *autolisp-reference-entry* (cons (cons 'return-values *autolisp-reference-value*) *autolisp-reference-entry*))

(setq *autolisp-reference-value* nil)

(setq *autolisp-reference-string* "Type: Integer\nA dimension of the array. The first dimension is dimension 1.")

(setq *autolisp-reference-value* (cons (cons "dim" *autolisp-reference-string*) *autolisp-reference-value*))

(setq *autolisp-reference-string* "Type: Safearray\nA variable containing a safearray.")

(setq *autolisp-reference-value* (cons (cons "var" *autolisp-reference-string*) *autolisp-reference-value*))

(setq *autolisp-reference-entry* (cons (cons 'arguments *autolisp-reference-value*) *autolisp-reference-entry*))

(setq *autolisp-reference-value* "(vlax-safearray-get-l-bound var dim)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns the lower boundary (starting index) of a dimension of an array")

(setq *autolisp-reference-entry* (cons (cons 'summary *autolisp-reference-value*) *autolisp-reference-entry*))

(setq *autolisp-reference-value* "vlax-safearray-get-l-bound (AutoLISP/ActiveX)")

(setq *autolisp-reference-entry* (cons (cons 'title *autolisp-reference-value*) *autolisp-reference-entry*))

(setq *autolisp-reference-value* "vlax-safearray-get-l-bound")

(setq *autolisp-reference-entry* (cons (cons 'name *autolisp-reference-value*) *autolisp-reference-entry*))

(setq *autolisp-reference-parts* (cons (list (cons "vlax-safearray-get-l-bound" *autolisp-reference-entry*)) *autolisp-reference-parts*))

(setq *autolisp-reference-entry* nil)

(setq *autolisp-reference-value* "GUID-07070F34-A919-4BF5-BBC9-6D940A93F765")

(setq *autolisp-reference-entry* (cons (cons 'guid *autolisp-reference-value*) *autolisp-reference-entry*))

(setq *autolisp-reference-value* "https://help.autodesk.com/cloudhelp/2023/ENU/AutoCAD-AutoLISP-Reference/files/GUID-07070F34-A919-4BF5-BBC9-6D940A93F765.htm")

(setq *autolisp-reference-entry* (cons (cons 'url *autolisp-reference-value*) *autolisp-reference-entry*))

(setq *autolisp-reference-value* "The following examples evaluate a safearray defined as follows:\n\n(vlax-make-safearray vlax-vbString '(1 . 2) '(0 . 1) ))\n\nGet the end index value of the array's first dimension:\n\n(vlax-safearray-get-u-bound tmatrix 1)\n2\n\nThe first dimension ends with index 2.\n\nGet the end index value of the second dimension of the array:\n\n(vlax-safearray-get-u-bound tmatrix 2)\n1\n\nThe second dimension starts with index 1.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer\nA numeric value representing the upper boundary (end index) of the dimension. If var is not an array, or dim is invalid (for example, 0, or a number greater than the number of dimensions in the array), an error results.")

(setq *autolisp-reference-entry* (cons (cons 'return-values *autolisp-reference-value*) *autolisp-reference-entry*))

(setq *autolisp-reference-value* nil)

(setq *autolisp-reference-string* "Type: Integer\nA dimension of the array. The first dimension is dimension 1.")

(setq *autolisp-reference-value* (cons (cons "dim" *autolisp-reference-string*) *autolisp-reference-value*))

(setq *autolisp-reference-string* "Type: Safearray\nA variable containing a safearray.")

(setq *autolisp-reference-value* (cons (cons "var" *autolisp-reference-string*) *autolisp-reference-value*))

(setq *autolisp-reference-entry* (cons (cons 'arguments *autolisp-reference-value*) *autolisp-reference-entry*))

(setq *autolisp-reference-value* "(vlax-safearray-get-u-bound var dim)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns the upper boundary (end index) of a dimension of an array")

(setq *autolisp-reference-entry* (cons (cons 'summary *autolisp-reference-value*) *autolisp-reference-entry*))

(setq *autolisp-reference-value* "vlax-safearray-get-u-bound (AutoLISP/ActiveX)")

(setq *autolisp-reference-entry* (cons (cons 'title *autolisp-reference-value*) *autolisp-reference-entry*))

(setq *autolisp-reference-value* "vlax-safearray-get-u-bound")

(setq *autolisp-reference-entry* (cons (cons 'name *autolisp-reference-value*) *autolisp-reference-entry*))

(setq *autolisp-reference-parts* (cons (list (cons "vlax-safearray-get-u-bound" *autolisp-reference-entry*)) *autolisp-reference-parts*))

(setq *autolisp-reference-entry* nil)

(setq *autolisp-reference-value* "GUID-D4D51BF6-E954-4EA8-9A8D-47FE61B860C6")

(setq *autolisp-reference-entry* (cons (cons 'guid *autolisp-reference-value*) *autolisp-reference-entry*))

(setq *autolisp-reference-value* "https://help.autodesk.com/cloudhelp/2023/ENU/AutoCAD-AutoLISP-Reference/files/GUID-D4D51BF6-E954-4EA8-9A8D-47FE61B860C6.htm")

(setq *autolisp-reference-entry* (cons (cons 'url *autolisp-reference-value*) *autolisp-reference-entry*))

(setq *autolisp-reference-value* "Create a single-dimension array consisting of doubles:\n\n(setq point (vlax-make-safearray vlax-vbDouble '(0 . 2)))\n#<safearray...>\n\nUse vlax-safearray-put-element to populate the array:\n\n(vlax-safearray-put-element point 0 100)\n100\n\n(vlax-safearray-put-element point 1 100)\n100\n\n(vlax-safearray-put-element point 2 0)\n0\n\nCreate a two-dimension array consisting of strings:\n\n(setq matrix (vlax-make-safearray vlax-vbString '(1 . 2) '(1 . 2) ))\n#<safearray...>\n\nUse vlax-safearray-put-element to populate the array:\n\n(vlax-safearray-put-element matrix 1 1 \"a\")\n\"a\"\n\n(vlax-safearray-put-element matrix 1 2 \"b\")\n\"b\"\n\n(vlax-safearray-put-element matrix 2 1 \"c\")\n\"c\"\n\n(vlax-safearray-put-element matrix 2 2 \"d\")\n\"d\"\n\nNote that you can also populate arrays using the vlax-safearray-fill function. The following function call accomplishes the same task as th")

(setq *autolisp-reference-value* (strcat *autolisp-reference-value* "ree vlax-safearray-put-element calls:\n\n(vlax-safearray-fill matrix '((\"a\" \"b\") (\"c\" \"d\")))\n#<safearray...>"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, VLA-object, Safearray, Variant, T, or nil\nThe value assigned to the element.")

(setq *autolisp-reference-entry* (cons (cons 'return-values *autolisp-reference-value*) *autolisp-reference-entry*))

(setq *autolisp-reference-value* nil)

(setq *autolisp-reference-string* "Type: Integer, Real, String, VLA-object, Safearray, Variant, T, or nil\nThe value to assign the safearray element.")

(setq *autolisp-reference-value* (cons (cons "value" *autolisp-reference-string*) *autolisp-reference-value*))

(setq *autolisp-reference-string* "Type: Integer\nA set of index values pointing to the element you are assigning a value to. For a single-dimension array, specify one index value; for a two-dimension array, specify two index values, and so on.")

(setq *autolisp-reference-value* (cons (cons "index ..." *autolisp-reference-string*) *autolisp-reference-value*))

(setq *autolisp-reference-string* "Type: Safearray\nA variable containing a safearray.")

(setq *autolisp-reference-value* (cons (cons "var" *autolisp-reference-string*) *autolisp-reference-value*))

(setq *autolisp-reference-entry* (cons (cons 'arguments *autolisp-reference-value*) *autolisp-reference-entry*))

(setq *autolisp-reference-value* "(vlax-safearray-put-element var index ... value)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Adds an element to an array")

(setq *autolisp-reference-entry* (cons (cons 'summary *autolisp-reference-value*) *autolisp-reference-entry*))

(setq *autolisp-reference-value* "vlax-safearray-put-element (AutoLISP/ActiveX)")

(setq *autolisp-reference-entry* (cons (cons 'title *autolisp-reference-value*) *autolisp-reference-entry*))

(setq *autolisp-reference-value* "vlax-safearray-put-element")

(setq *autolisp-reference-entry* (cons (cons 'name *autolisp-reference-value*) *autolisp-reference-entry*))

(setq *autolisp-reference-parts* (cons (list (cons "vlax-safearray-put-element" *autolisp-reference-entry*)) *autolisp-reference-parts*))

(setq *autolisp-reference-entry* nil)

(setq *autolisp-reference-value* "GUID-64051CE8-BDDF-4AFF-A440-B93F1E24AF78")

(setq *autolisp-reference-entry* (cons (cons 'guid *autolisp-reference-value*) *autolisp-reference-entry*))

(setq *autolisp-reference-value* "https://help.autodesk.com/cloudhelp/2023/ENU/AutoCAD-AutoLISP-Reference/files/GUID-64051CE8-BDDF-4AFF-A440-B93F1E24AF78.htm")

(setq *autolisp-reference-entry* (cons (cons 'url *autolisp-reference-value*) *autolisp-reference-entry*))

(setq *autolisp-reference-value* "Create a single-dimension array of doubles and a two-dimension array of strings:\n\n(setq point (vlax-make-safearray vlax-vbDouble '(0 . 2)))\n#<safearray...>\n\n(setq matrix (vlax-make-safearray vlax-vbString '(1 . 2) '(1 . 2) ))\n#<safearray...>\n\nUse vlax-safearray-type to verify the data type of the safearrays:\n\n(vlax-safearray-type point)\n5\n\n(vlax-safearray-type matrix)\n8")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer or error\nIf var contains a safearray, one of the following numeric values is returned:\n2 -- Integer (vlax-vbInteger)\n3 -- Long integer (vlax-vbLong)\n4 -- Single-precision floating-point number (vlax-vbSingle)\n5 -- Double-precision floating-point number (vlax-vbDouble)\n8 -- String (vlax-vbString)\n9 -- Object (vlax-vbObject)\n11 -- Boolean (vlax-vbBoolean)\n12 -- Variant (vlax-vbVariant)\nIf var does not contain a safearray, an error results.")

(setq *autolisp-reference-entry* (cons (cons 'return-values *autolisp-reference-value*) *autolisp-reference-entry*))

(setq *autolisp-reference-value* nil)

(setq *autolisp-reference-string* "Type: Safearray\nA variable containing a safearray.")

(setq *autolisp-reference-value* (cons (cons "var" *autolisp-reference-string*) *autolisp-reference-value*))

(setq *autolisp-reference-entry* (cons (cons 'arguments *autolisp-reference-value*) *autolisp-reference-entry*))

(setq *autolisp-reference-value* "(vlax-safearray-type var)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns the data type of a safearray")

(setq *autolisp-reference-entry* (cons (cons 'summary *autolisp-reference-value*) *autolisp-reference-entry*))

(setq *autolisp-reference-value* "vlax-safearray-type (AutoLISP/ActiveX)")

(setq *autolisp-reference-entry* (cons (cons 'title *autolisp-reference-value*) *autolisp-reference-entry*))

(setq *autolisp-reference-value* "vlax-safearray-type")

(setq *autolisp-reference-entry* (cons (cons 'name *autolisp-reference-value*) *autolisp-reference-entry*))

(setq *autolisp-reference-parts* (cons (list (cons "vlax-safearray-type" *autolisp-reference-entry*)) *autolisp-reference-parts*))

(setq *autolisp-reference-entry* nil)

(setq *autolisp-reference-value* "GUID-7B1BBCDD-69DD-40E6-81CB-370A05725431")

(setq *autolisp-reference-entry* (cons (cons 'guid *autolisp-reference-value*) *autolisp-reference-entry*))

(setq *autolisp-reference-value* "https://help.autodesk.com/cloudhelp/2023/ENU/AutoCAD-AutoLISP-Reference/files/GUID-7B1BBCDD-69DD-40E6-81CB-370A05725431.htm")

(setq *autolisp-reference-entry* (cons (cons 'url *autolisp-reference-value*) *autolisp-reference-entry*))

(setq *autolisp-reference-value* "Define a transformation matrix and assign its value to variable tmatrix:\n\n(setq tmatrix (vlax-tmatrix '((1 1 1 0) (1 2 3 0) (2 3 4 5) (2 9 8 3))))\n#<variant 8197 ...>\n\nUse vlax-safearray->list to view the value of tmatrix in list form:\n\n(vlax-safearray->list (vlax-variant-value tmatrix))\n((1.0 1.0 1.0 0.0) (1.0 2.0 3.0 0.0) (2.0 3.0 4.0 5.0) (2.0 9.0 8.0 3.0))\n\nThe following code example creates a line and rotates it 90 degrees using a transformation matrix:\n\n(defun Example_TransformBy ( / acadObject acadDocument mSpace lineObj\n                               startPt endPt matList transMat)\n  (vl-load-com)      ; Load ActiveX support\n  (setq acadObject   (vlax-get-acad-object))\n  (setq acadDocument (vla-get-ActiveDocument acadObject))\n  (setq mSpace       (vla-get-ModelSpace acadDocument))\n\n;;; Create a line\n  (setq startPt (getpoint \"\\nPick the start point: \"))\n  ")

(setq *autolisp-reference-value* (strcat *autolisp-reference-value* "(setq endPt   (vlax-3d-point (getpoint startPt \"\\nPick the end point: \")))\n  (setq lineObj (vla-addline mSpace (vlax-3d-point startPt) endPt))\n\n;;; Initialize the transMat variable with a transformation matrix\n;;; that will rotate an object by 90 degrees about the point(0,0,0).\n;;; Begin by Creating a list of four lists, each containing four\n;;; numbers, representing transformation matrix elements.\n  (setq matList (list '(0 -1 0 0) '(1 0 0 0) '(0 0 1 0) '(0 0 0 1)))\n\n;;; Use vlax-tmatrix to convert the list to a variant.\n  (setq transmat (vlax-tmatrix matlist))\n\n;;; Transform the line using the defined transformation matrix\n  (vla-transformby lineObj transMat)\n  (vla-zoomall acadObject)\n  (prompt \"\\nThe line has been transformed.\")\n (princ)\n)"))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Variant\nA variant of type safearray, representing the 4×4 transformation matrix.")

(setq *autolisp-reference-entry* (cons (cons 'return-values *autolisp-reference-value*) *autolisp-reference-entry*))

(setq *autolisp-reference-value* nil)

(setq *autolisp-reference-string* "Type: List\nA value of four lists, each containing four numbers, representing transformation matrix elements.")

(setq *autolisp-reference-value* (cons (cons "lst" *autolisp-reference-string*) *autolisp-reference-value*))

(setq *autolisp-reference-entry* (cons (cons 'arguments *autolisp-reference-value*) *autolisp-reference-entry*))

(setq *autolisp-reference-value* "(vlax-tmatrix lst)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns a suitable representation for a 4 x 4 transformation matrix to be used in VLA methods")

(setq *autolisp-reference-entry* (cons (cons 'summary *autolisp-reference-value*) *autolisp-reference-entry*))

(setq *autolisp-reference-value* "vlax-tmatrix (AutoLISP/ActiveX)")

(setq *autolisp-reference-entry* (cons (cons 'title *autolisp-reference-value*) *autolisp-reference-entry*))

(setq *autolisp-reference-value* "vlax-tmatrix")

(setq *autolisp-reference-entry* (cons (cons 'name *autolisp-reference-value*) *autolisp-reference-entry*))

(setq *autolisp-reference-parts* (cons (list (cons "vlax-tmatrix" *autolisp-reference-entry*)) *autolisp-reference-parts*))

(setq *autolisp-reference-parts*
  (cons
    '(("vlax-typeinfo-available-p" .
          ((name . "vlax-typeinfo-available-p")
           (title . "vlax-typeinfo-available-p (AutoLISP/ActiveX)")
           (summary . "Determines whether TypeLib information is present for the specified type of object")
           (source-kind . "AutoLISP/ActiveX")
           (alphabetic-group . "V")
           (feature-groups . ("Drawing Object Functions Reference (AutoLISP/ActiveX)" "Object-Handling" "Object-Handling Functions Reference (AutoLISP/ActiveX)"))
           (supported-platforms . "Windows only")
           (signature . "(vlax-typeinfo-available-p obj)")
           (arguments . (("obj" . "Type: VLA-object\nAn object.")))
           (return-values . "Type: T or nil\nT, if TypeLib information is available; otherwise nil.")
           (release-information . nil)
           (history . nil)
           (examples . "N/A")
           (url . "https://help.autodesk.com/cloudhelp/2023/ENU/AutoCAD-AutoLISP-Reference/files/GUID-1DAB4433-A0FA-43EA-9022-68C8E468B1EA.htm")
           (guid . "GUID-1DAB4433-A0FA-43EA-9022-68C8E468B1EA"))))
    *autolisp-reference-parts*))

(setq *autolisp-reference-parts*
  (cons
    '(("vlax-user-product-key" .
          ((name . "vlax-user-product-key")
           (title . "vlax-user-product-key (AutoLISP/ActiveX)")
           (summary . "Returns the AutoCAD Windows registry path in the HKCU (HKEY_CURRENT_USER)")
           (source-kind . "AutoLISP/ActiveX")
           (alphabetic-group . "V")
           (feature-groups . ("Windows Registry and Property List File"))
           (supported-platforms . "Windows only")
           (signature . "(vlax-user-product-key)")
           (arguments . nil)
           (return-values . "Type: String\nA value containing the AutoCAD registry path.")
           (release-information . nil)
           (history . nil)
           (examples . "(vlax-user-product-key)\n\"Software\\\\Autodesk\\\\AutoCAD\\\\R24.2\\\\ACAD-6101:409\"")
           (url . "https://help.autodesk.com/cloudhelp/2023/ENU/AutoCAD-AutoLISP-Reference/files/GUID-42C8BADD-C5BC-4913-A8AF-ECF2ADF42FB6.htm")
           (guid . "GUID-42C8BADD-C5BC-4913-A8AF-ECF2ADF42FB6"))))
    *autolisp-reference-parts*))

(setq *autolisp-reference-entry* nil)

(setq *autolisp-reference-value* "GUID-64714B92-0662-496E-8C9B-99DFCE7CAFB1")

(setq *autolisp-reference-entry* (cons (cons 'guid *autolisp-reference-value*) *autolisp-reference-entry*))

(setq *autolisp-reference-value* "https://help.autodesk.com/cloudhelp/2023/ENU/AutoCAD-AutoLISP-Reference/files/GUID-64714B92-0662-496E-8C9B-99DFCE7CAFB1.htm")

(setq *autolisp-reference-entry* (cons (cons 'url *autolisp-reference-value*) *autolisp-reference-entry*))

(setq *autolisp-reference-value* "Set a variable named varint to a variant value:\n\n(setq variant (vlax-make-variant 5))\n#<variant 3 5>\n\nSet a variable named variantStr to the value contained in variant, but convert that value to a string:\n\n(setq variantStr (vlax-variant-change-type variant vlax-vbstring))\n#<variant 8 5>\n\nCheck the value of variantStr:\n\n(vlax-variant-value variantStr)\n\"5\"\n\nThis confirms that variantStr contains a string.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer, Real, String, VLA-object, safearray, T, or nil\nThe value of var, after converting it to the specified variant type; otherwise nil, if var could not be converted to the specified type.")

(setq *autolisp-reference-entry* (cons (cons 'return-values *autolisp-reference-value*) *autolisp-reference-entry*))

(setq *autolisp-reference-value* nil)

(setq *autolisp-reference-string* "Type: Integer\nThe type of variant to return, using the value of var (the value of var is unchanged). The type value can be represented by one of the following constants:\nvlax-vbEmpty (0) -- Uninitialized\nvlax-vbNull (1) -- Contains no valid data\nvlax-vbInteger (2) -- Integer\nvlax-vbLong (3) -- Long integer\nvlax-vbSingle (4) -- Single-precision floating-point number\nvlax-vbDouble (5) -- Double-precision floating-point number\nvlax-vbString (8) -- String\nvlax-vbObject (9) -- Object\nvlax-vbBoolean (11) -- Boolean\nvlax-vbArray (8192) -- Array\nThe integer shown in parentheses indicates the value to which the constant evaluates. It is recommended that you specify the constant in your argument, not the integer value, in case the value changes in later releases of AutoCAD.")

(setq *autolisp-reference-value* (cons (cons "type" *autolisp-reference-string*) *autolisp-reference-value*))

(setq *autolisp-reference-string* "Type: Variant\nA variable containing a variant.")

(setq *autolisp-reference-value* (cons (cons "var" *autolisp-reference-string*) *autolisp-reference-value*))

(setq *autolisp-reference-entry* (cons (cons 'arguments *autolisp-reference-value*) *autolisp-reference-entry*))

(setq *autolisp-reference-value* "(vlax-variant-change-type var type)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns the value of a variant after changing it from one data type to another")

(setq *autolisp-reference-entry* (cons (cons 'summary *autolisp-reference-value*) *autolisp-reference-entry*))

(setq *autolisp-reference-value* "vlax-variant-change-type (AutoLISP/ActiveX)")

(setq *autolisp-reference-entry* (cons (cons 'title *autolisp-reference-value*) *autolisp-reference-entry*))

(setq *autolisp-reference-value* "vlax-variant-change-type")

(setq *autolisp-reference-entry* (cons (cons 'name *autolisp-reference-value*) *autolisp-reference-entry*))

(setq *autolisp-reference-parts* (cons (list (cons "vlax-variant-change-type" *autolisp-reference-entry*)) *autolisp-reference-parts*))

(setq *autolisp-reference-entry* nil)

(setq *autolisp-reference-value* "GUID-14029CC8-2839-432B-ABFC-F470AFA7606B")

(setq *autolisp-reference-entry* (cons (cons 'guid *autolisp-reference-value*) *autolisp-reference-entry*))

(setq *autolisp-reference-value* "https://help.autodesk.com/cloudhelp/2023/ENU/AutoCAD-AutoLISP-Reference/files/GUID-14029CC8-2839-432B-ABFC-F470AFA7606B.htm")

(setq *autolisp-reference-entry* (cons (cons 'url *autolisp-reference-value*) *autolisp-reference-entry*))

(setq *autolisp-reference-value* "Set a variant to nil and display the variant's data type:\n\n(setq varnil (vlax-make-variant nil))\n#<variant 0 >\n\n(vlax-variant-type varnil)\n0\n\nSet a variant to an integer value and explicitly define the variant as an integer data type:\n\n(setq varint (vlax-make-variant 5 vlax-vbInteger))\n#<variant 2 5>\n\n(vlax-variant-type varint)\n2\n\nSet a variant to an integer value and display the variant's data type:\n\n(setq varint (vlax-make-variant 5))\n#<variant 3 5>\n\n(vlax-variant-type varint)\n3\n\nNotice that without explicitly defining the data type to vlax-variant-variant, an integer assignment results in a Long integer data type.\n\nSet a variant to a string and display the variant's data type:\n\n(setq varstr (vlax-make-variant \"ghost\"))\n#<variant 8 ghost>\n\n(vlax-variant-type varstr)\n8\n\nCreate a safearray of doubles, assign the safearray to a variant, and display the ")

(setq *autolisp-reference-value* (strcat *autolisp-reference-value* "variant's data type:\n\n(setq 4dubs (vlax-make-safearray vlax-vbDouble '(0 . 3)))\n#<safearray...>\n\n(setq var4dubs (vlax-make-variant 4dubs))\n#<variant 8197 ...>\n\n(vlax-variant-type var4dubs)\n8197\n\nA variant type value greater than 8192 indicates that the variant contains some type of safearray. Subtract 8192 from the return value to determine the data type of the safearray. In this example, 8197-8192=5 (vlax-vbDouble).\n\nAssign a real value to a variable, then issue vlax-variant-type to check the variable's data type:\n\n(setq notvar 6.0)\n6.0\n\n(vlax-variant-type notvar)\n; *** ERROR: bad argument type: variantp 6.0\n\nThis last example results in an error, because the variable passed to vlax-variant-type does not contain a variant."))

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer\nIf var contains a variant, one of the following numeric values is returned:\n0 -- Uninitialized (vlax-vbEmpty)\n1 -- Contains no valid data (vlax-vbNull)\n2 -- Integer (vlax-vbInteger)\n3 -- Long integer (vlax-vbLong)\n4 -- Single-precision floating-point number (vlax-vbSingle)\n5 -- Double-precision floating-point number (vlax-vbDouble)\n8 -- String (vlax-vbString)\n9 -- Object (vlax-vbObject)\n11 -- Boolean (vlax-vbBoolean)\n8192+n -- Safearray (vlax-vbArray) of some data type. For example, an array of doubles (vlax-vbDouble) returns 8197 (8192 + 5).\nIf var does not contain a variant, an error results.")

(setq *autolisp-reference-entry* (cons (cons 'return-values *autolisp-reference-value*) *autolisp-reference-entry*))

(setq *autolisp-reference-value* nil)

(setq *autolisp-reference-string* "Type: Variant\nA variable containing a variant.")

(setq *autolisp-reference-value* (cons (cons "var" *autolisp-reference-string*) *autolisp-reference-value*))

(setq *autolisp-reference-entry* (cons (cons 'arguments *autolisp-reference-value*) *autolisp-reference-entry*))

(setq *autolisp-reference-value* "(vlax-variant-type var)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Data Conversion Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Determines the data type of a variant")

(setq *autolisp-reference-entry* (cons (cons 'summary *autolisp-reference-value*) *autolisp-reference-entry*))

(setq *autolisp-reference-value* "vlax-variant-type (AutoLISP/ActiveX)")

(setq *autolisp-reference-entry* (cons (cons 'title *autolisp-reference-value*) *autolisp-reference-entry*))

(setq *autolisp-reference-value* "vlax-variant-type")

(setq *autolisp-reference-entry* (cons (cons 'name *autolisp-reference-value*) *autolisp-reference-entry*))

(setq *autolisp-reference-parts* (cons (list (cons "vlax-variant-type" *autolisp-reference-entry*)) *autolisp-reference-parts*))

(setq *autolisp-reference-parts*
  (cons
    '(("vlax-variant-value" .
          ((name . "vlax-variant-value")
           (title . "vlax-variant-value (AutoLISP/ActiveX)")
           (summary . "Returns the value of a variant")
           (source-kind . "AutoLISP/ActiveX")
           (alphabetic-group . "V")
           (feature-groups . ("Data Conversion Functions Reference (AutoLISP/ActiveX)"))
           (supported-platforms . "Windows only")
           (signature . "(vlax-variant-value var)")
           (arguments . (("var" . "Type: Variant\nA variable containing a variant.")))
           (return-values . "Type: Integer, Real, String, VLA-object, Safearray, T, or nil\nThe value of the variable. If the variable does not contain a variant, an error occurs.")
           (release-information . nil)
           (history . nil)
           (examples . "(vlax-variant-value varstr)\n\"ghost\"\n\n(vlax-variant-value varint)\n5\n\n(vlax-variant-value notvar)\n; *** ERROR: bad argument type: variantp 6.0\n\nThe last example results in an error, because notvar does not contain a variant.")
           (url . "https://help.autodesk.com/cloudhelp/2023/ENU/AutoCAD-AutoLISP-Reference/files/GUID-D26E25ED-6D9A-4E0F-B7C3-CC10F95246F9.htm")
           (guid . "GUID-D26E25ED-6D9A-4E0F-B7C3-CC10F95246F9"))))
    *autolisp-reference-parts*))

(setq *autolisp-reference-parts*
  (cons
    '(("vlax-vla-object->ename" .
          ((name . "vlax-vla-object->ename")
           (title . "vlax-vla-object->ename (AutoLISP/ActiveX)")
           (summary . "Transforms a VLA-object to an AutoLISP entity")
           (source-kind . "AutoLISP/ActiveX")
           (alphabetic-group . "V")
           (feature-groups . ("Data Conversion Functions Reference (AutoLISP/ActiveX)"))
           (supported-platforms . "Windows only")
           (signature . "(vlax-vla-object->ename obj)")
           (arguments . (("obj" . "Type: VLA-object\nAn object.")))
           (return-values . "Type: Ename (entity name)\nAn entity name.")
           (release-information . nil)
           (history . nil)
           (examples . "(vlax-vla-object->ename vlaobj)\n<Entity name: 27e0540>")
           (url . "https://help.autodesk.com/cloudhelp/2023/ENU/AutoCAD-AutoLISP-Reference/files/GUID-9127B839-D275-473F-A166-59BE94AEFACB.htm")
           (guid . "GUID-9127B839-D275-473F-A166-59BE94AEFACB"))))
    *autolisp-reference-parts*))

(setq *autolisp-reference-parts*
  (cons
    '(("vlax-write-enabled-p" .
          ((name . "vlax-write-enabled-p")
           (title . "vlax-write-enabled-p (AutoLISP/ActiveX)")
           (summary . "Determines if an AutoCAD drawing object can be modified")
           (source-kind . "AutoLISP/ActiveX")
           (alphabetic-group . "V")
           (feature-groups . ("Drawing Object Functions Reference (AutoLISP/ActiveX)" "Object-Handling" "Object-Handling Functions Reference (AutoLISP/ActiveX)"))
           (supported-platforms . "Windows only")
           (signature . "(vlax-write-enabled-p obj)")
           (arguments . (("obj" . "Type: VLA-object or Ename (entity name)\nAn object or entity name.")))
           (return-values . "Type: T or nil\nT, if the AutoCAD drawing object can be modified, nil if the object cannot be modified.")
           (release-information . nil)
           (history . nil)
           (examples . "N/A")
           (url . "https://help.autodesk.com/cloudhelp/2023/ENU/AutoCAD-AutoLISP-Reference/files/GUID-67DAD30A-B359-4566-9B11-C6203EB71247.htm")
           (guid . "GUID-67DAD30A-B359-4566-9B11-C6203EB71247"))))
    *autolisp-reference-parts*))

(setq *autolisp-reference-entry* nil)

(setq *autolisp-reference-value* "GUID-8184531C-EDE5-4949-9EAE-25CE98BFF89C")

(setq *autolisp-reference-entry* (cons (cons 'guid *autolisp-reference-value*) *autolisp-reference-entry*))

(setq *autolisp-reference-value* "https://help.autodesk.com/cloudhelp/2023/ENU/AutoCAD-AutoLISP-Reference/files/GUID-8184531C-EDE5-4949-9EAE-25CE98BFF89C.htm")

(setq *autolisp-reference-entry* (cons (cons 'url *autolisp-reference-value*) *autolisp-reference-entry*))

(setq *autolisp-reference-value* "Assuming that yinyang.lsp resides in a directory that is in the AutoCAD support file search path, the following command compiles this program:\n\n(vlisp-compile 'st \"yinyang.lsp\")\nT\n\nThe output file is named yinyang.fas and resides in the same directory as the source file.\n\nThe following command compiles yinyang.lsp and names the output file GoodKarma.fas:\n\n(vlisp-compile 'st \"yinyang.lsp\" \"GoodKarma.fas\")\n\nNote that the output file from the previous command resides in the AutoCAD installation directory, not the directory where yinyang.lsp resides. The following command compiles yinyang.lsp and directs the output file to the c:\\my documents directory:\n\n(vlisp-compile 'st \"yinyang.lsp\" \"c:/my documents/GoodKarma\")\n\nThis last example identifies the full path of the file to be compiled:\n\n(vlisp-compile 'st \"<AutoCAD installation directory>/Sample/yinyang.lsp\")\n")

(setq *autolisp-reference-value* (strcat *autolisp-reference-value* "\nThe output file from this command is named yinyang.fas and resides in the same directory as the input file."))

(setq *autolisp-reference-entry* (cons (cons 'examples *autolisp-reference-value*) *autolisp-reference-entry*))

(setq *autolisp-reference-value* "AutoCAD 2021\n- Updated to support the Unicode file format.")

(setq *autolisp-reference-entry* (cons (cons 'history *autolisp-reference-value*) *autolisp-reference-entry*))

(setq *autolisp-reference-value* "Releases:\n- AutoCAD R14 and later on Windows")

(setq *autolisp-reference-entry* (cons (cons 'release-information *autolisp-reference-value*) *autolisp-reference-entry*))

(setq *autolisp-reference-value* "Type: T or nil\nT, if compilation is successful; otherwise nil.")

(setq *autolisp-reference-entry* (cons (cons 'return-values *autolisp-reference-value*) *autolisp-reference-entry*))

(setq *autolisp-reference-value* nil)

(setq *autolisp-reference-string* "Type: String\nCompiled output file name. If you do not specify an output file, vlisp-compile names the output with the same name as the input file, but replaces the extension with .fas.\nNote: If you specify an output file name but do not specify a path name for either the input or the output file, vlisp-compile places the output file in the AutoCAD installation directory.")

(setq *autolisp-reference-value* (cons (cons "output-filename" *autolisp-reference-string*) *autolisp-reference-value*))

(setq *autolisp-reference-string* "Type: String\nAutoLISP source file name. If the source file is in the AutoCAD support file search path, you can omit the path when specifying the file name. If you omit the file extension, .lspis assumed.")

(setq *autolisp-reference-value* (cons (cons "filename" *autolisp-reference-string*) *autolisp-reference-value*))

(setq *autolisp-reference-string* "Type: Symbol\nThe compiler mode, which can be one of the following symbols:\nst Standard build mode - Produces the smallest output file and is suitable for programs consisting of a single file.\nlsm Optimize and link indirectly - Optimizes the compiled files, but does not create direct references to the compiled functions in the compiled code.\nlsa Optimize and link directly - Optimizes the compiled files and creates direct references to the compiled function in the compiled code, instead of to the function symbol.\nNote: Both the optimization options are best suited for large and complex programs.\nThe basic functions of optimization are as follows:\n- Link function calls to create direct references to the compiled function in the compiled code, instead of to the function symbol. This feature improves the performance of the compiled code and protects the code against function redefiniti")

(setq *autolisp-reference-string* (strcat *autolisp-reference-string* "on at runtime.\n- Drop function names to make the compiled code more secure and to decrease program size and load time.\n- Drop the names of all local variables and directly link their references. This also makes the compiled code more secure and decreases program size and load time."))

(setq *autolisp-reference-value* (cons (cons "mode" *autolisp-reference-string*) *autolisp-reference-value*))

(setq *autolisp-reference-entry* (cons (cons 'arguments *autolisp-reference-value*) *autolisp-reference-entry*))

(setq *autolisp-reference-value* "(vlisp-compile 'mode filename [output-filename])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* nil)

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/Visual LISP IDE")

(setq *autolisp-reference-entry* (cons (cons 'source-kind *autolisp-reference-value*) *autolisp-reference-entry*))

(setq *autolisp-reference-value* "Compiles AutoLISP source code into a FAS file")

(setq *autolisp-reference-entry* (cons (cons 'summary *autolisp-reference-value*) *autolisp-reference-entry*))

(setq *autolisp-reference-value* "vlisp-compile (AutoLISP/Visual LISP IDE)")

(setq *autolisp-reference-entry* (cons (cons 'title *autolisp-reference-value*) *autolisp-reference-entry*))

(setq *autolisp-reference-value* "vlisp-compile")

(setq *autolisp-reference-entry* (cons (cons 'name *autolisp-reference-value*) *autolisp-reference-entry*))

(setq *autolisp-reference-parts* (cons (list (cons "vlisp-compile" *autolisp-reference-entry*)) *autolisp-reference-parts*))

(setq *autolisp-reference-entry* nil)

(setq *autolisp-reference-value* "GUID-510EC430-4F09-463E-8FAC-58D8B0B64EB8")

(setq *autolisp-reference-entry* (cons (cons 'guid *autolisp-reference-value*) *autolisp-reference-entry*))

(setq *autolisp-reference-value* "https://help.autodesk.com/cloudhelp/2023/ENU/AutoCAD-AutoLISP-Reference/files/GUID-510EC430-4F09-463E-8FAC-58D8B0B64EB8.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Database reactor events:\n- Database reactor events Name Event :vlr-objectAppended An object has been appended to the drawing database. :vlr-objectUnAppended An object has been detached from the drawing database, e.g., by using UNDO. :vlr-objectReAppended A detached object has been restored in the drawing database, e.g., by using REDO. :vlr-objectOpenedForModify An object is about to be changed. :vlr-objectModified An object has been changed. :vlr-objectErased An object has been flagged as being erased. :vlr-objectUnErased An object's erased-flag has been removed.\n- callback_function is a symbol representing a function to be called when the event fires. Each callback function accepts two arguments:\n- reactor_object -- The VLR object that called the callback functio")

(setq *autolisp-reference-string* (strcat *autolisp-reference-string* "n\n- obj -- The database object associated with the event"))

(setq *autolisp-reference-value* (cons (cons "callbacks" *autolisp-reference-string*) *autolisp-reference-value*))

(setq *autolisp-reference-string* "Type: Integer, Real, String, List, VLA-object, Safearray, Variant, T, or nil\nAny AutoLISP data to be associated with a reactor object; otherwise nil, if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-acdb-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs a reactor object that notifies when an object is added to, modified in, or erased from a drawing database")

(setq *autolisp-reference-entry* (cons (cons 'summary *autolisp-reference-value*) *autolisp-reference-entry*))

(setq *autolisp-reference-value* "vlr-acdb-reactor (AutoLISP/ActiveX)")

(setq *autolisp-reference-entry* (cons (cons 'title *autolisp-reference-value*) *autolisp-reference-entry*))

(setq *autolisp-reference-value* "vlr-acdb-reactor")

(setq *autolisp-reference-entry* (cons (cons 'name *autolisp-reference-value*) *autolisp-reference-entry*))

(setq *autolisp-reference-parts* (cons (list (cons "vlr-acdb-reactor" *autolisp-reference-entry*)) *autolisp-reference-parts*))

(setq *autolisp-reference-parts*
  (cons
    '(("vlr-add" .
          ((name . "vlr-add")
           (title . "vlr-add (AutoLISP/ActiveX)")
           (summary . "Enables a disabled reactor object")
           (source-kind . "AutoLISP/ActiveX")
           (alphabetic-group . "V")
           (feature-groups . ("Reactor Functions Reference (AutoLISP/ActiveX)"))
           (supported-platforms . "Windows only")
           (signature . "(vlr-add obj)")
           (arguments . (("obj" . "Type: VLR object\nA object representing the reactor to be enabled.")))
           (return-values . "Type: VLR object\nThe obj argument.")
           (release-information . nil)
           (history . nil)
           (examples . "N/A")
           (url . "https://help.autodesk.com/cloudhelp/2023/ENU/AutoCAD-AutoLISP-Reference/files/GUID-E4BDCF87-505B-4B94-810E-C1AF0D289C7D.htm")
           (guid . "GUID-E4BDCF87-505B-4B94-810E-C1AF0D289C7D"))))
    *autolisp-reference-parts*))

(setq *autolisp-reference-parts*
  (cons
    '(("vlr-added-p" .
          ((name . "vlr-added-p")
           (title . "vlr-added-p (AutoLISP/ActiveX)")
           (summary . "Tests to determine if a reactor object is enabled")
           (source-kind . "AutoLISP/ActiveX")
           (alphabetic-group . "V")
           (feature-groups . ("Reactor Functions Reference (AutoLISP/ActiveX)"))
           (supported-platforms . "Windows only")
           (signature . "(vlr-added-p obj)")
           (arguments . (("obj" . "Type: VLR object\nA object representing the reactor to be tested.")))
           (return-values . "Type: T or nil\nT if the specified reactor is enabled; otherwise nil if the reactor is disabled.")
           (release-information . nil)
           (history . nil)
           (examples . "N/A")
           (url . "https://help.autodesk.com/cloudhelp/2023/ENU/AutoCAD-AutoLISP-Reference/files/GUID-0B20B565-5C65-4BA5-B0AC-08C5DDA19804.htm")
           (guid . "GUID-0B20B565-5C65-4BA5-B0AC-08C5DDA19804"))))
    *autolisp-reference-parts*))

(setq *autolisp-reference-parts*
  (cons
    '(("vlr-beep-reaction" .
          ((name . "vlr-beep-reaction")
           (title . "vlr-beep-reaction (AutoLISP/ActiveX)")
           (summary . "Produces a beep sound")
           (source-kind . "AutoLISP/ActiveX")
           (alphabetic-group . "V")
           (feature-groups . ("Reactor Functions Reference (AutoLISP/ActiveX)"))
           (supported-platforms . "Windows only")
           (signature . "(vlr-beep-reaction [args ...])")
           (arguments . (("args" . "Type: Integer, Real, String, List, File, VLA-object, Safearray, Variant, Ename (entity name), T, or nil\nAny value that can be used a reactor.")))
           (return-values . "Type: nil\nAlways returns nil.")
           (release-information . nil)
           (history . nil)
           (examples . "N/A")
           (url . "https://help.autodesk.com/cloudhelp/2023/ENU/AutoCAD-AutoLISP-Reference/files/GUID-47765811-714A-455C-87FF-806B21483CD8.htm")
           (guid . "GUID-47765811-714A-455C-87FF-806B21483CD8"))))
    *autolisp-reference-parts*))

(setq *autolisp-reference-entry* nil)

(setq *autolisp-reference-value* "GUID-9D4F05F7-E3D2-4AC6-B6EB-0E938C2A68FA")

(setq *autolisp-reference-entry* (cons (cons 'guid *autolisp-reference-value*) *autolisp-reference-entry*))

(setq *autolisp-reference-value* "https://help.autodesk.com/cloudhelp/2023/ENU/AutoCAD-AutoLISP-Reference/files/GUID-9D4F05F7-E3D2-4AC6-B6EB-0E938C2A68FA.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function )\n- event-name is one of the following Command reactor events:\n- Command reactor events Event name Description :vlr-unknownCommand A command not known to AutoCAD was issued. :vlr-commandWillStart An AutoCAD command has been called. :vlr-commandEnded An AutoCAD command has completed. :vlr-commandCancelled An AutoCAD command has been canceled. :vlr-commandFailed An AutoCAD command failed to complete.\n- callback_function is a symbol representing a function to be called when the event fires.\n- Each callback function accepts two arguments:\n- reactor_object -- The VLR object that called the callback function.\n- list -- A list containing a single element, the string identifying the command.")

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data is to be associated with the reactor.")

(setq *autolisp-reference-value* (cons (cons "data" *autolisp-reference-string*) *autolisp-reference-value*))

(setq *autolisp-reference-entry* (cons (cons 'arguments *autolisp-reference-value*) *autolisp-reference-entry*))

(setq *autolisp-reference-value* "(vlr-command-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor that notifies of a command event")

(setq *autolisp-reference-entry* (cons (cons 'summary *autolisp-reference-value*) *autolisp-reference-entry*))

(setq *autolisp-reference-value* "vlr-command-reactor (AutoLISP/ActiveX)")

(setq *autolisp-reference-entry* (cons (cons 'title *autolisp-reference-value*) *autolisp-reference-entry*))

(setq *autolisp-reference-value* "vlr-command-reactor")

(setq *autolisp-reference-entry* (cons (cons 'name *autolisp-reference-value*) *autolisp-reference-entry*))

(setq *autolisp-reference-parts* (cons (list (cons "vlr-command-reactor" *autolisp-reference-entry*)) *autolisp-reference-parts*))

(setq *autolisp-reference-parts*
  (cons
    '(("vlr-current-reaction-name" .
          ((name . "vlr-current-reaction-name")
           (title . "vlr-current-reaction-name (AutoLISP/ActiveX)")
           (summary . "Returns the name (symbol) of the current event, if called from within a reactor's callback")
           (source-kind . "AutoLISP/ActiveX")
           (alphabetic-group . "V")
           (feature-groups . ("Reactor Functions Reference (AutoLISP/ActiveX)"))
           (supported-platforms . "Windows only")
           (signature . "(vlr-current-reaction-name)")
           (arguments . nil)
           (return-values . "Type: VLR object\nA symbol indicating the event that triggered the reactor.")
           (release-information . nil)
           (history . nil)
           (examples . "N/A")
           (url . "https://help.autodesk.com/cloudhelp/2023/ENU/AutoCAD-AutoLISP-Reference/files/GUID-48D0783B-28D7-47EE-88EF-5403FD5016CA.htm")
           (guid . "GUID-48D0783B-28D7-47EE-88EF-5403FD5016CA"))))
    *autolisp-reference-parts*))

(setq *autolisp-reference-parts*
  (cons
    '(("vlr-data" .
          ((name . "vlr-data")
           (title . "vlr-data (AutoLISP/ActiveX)")
           (summary . "Returns application-specific data associated with a reactor")
           (source-kind . "AutoLISP/ActiveX")
           (alphabetic-group . "V")
           (feature-groups . ("Reactor Functions Reference (AutoLISP/ActiveX)"))
           (supported-platforms . "Windows only")
           (signature . "(vlr-data obj)")
           (arguments . (("obj" . "Type: VLR object\nA object representing the reactor object from which to extract data.")))
           (return-values . "Type: Integer, Real, String, List, VLA-object, Safearray, Variant, T, or nil\nThe application-specific data obtained from the reactor object.")
           (release-information . nil)
           (history . nil)
           (examples . "The following example obtains a string associated with the circleReactor VLR object:\n\n(vlr-data circleReactor)\n\"Circle Reactor\"")
           (url . "https://help.autodesk.com/cloudhelp/2023/ENU/AutoCAD-AutoLISP-Reference/files/GUID-55830A47-2AEF-4565-BB5B-F5A7629CC567.htm")
           (guid . "GUID-55830A47-2AEF-4565-BB5B-F5A7629CC567"))))
    *autolisp-reference-parts*))

(setq *autolisp-reference-parts*
  (cons
    '(("vlr-data-set" .
          ((name . "vlr-data-set")
           (title . "vlr-data-set (AutoLISP/ActiveX)")
           (summary . "Overwrites application-specific data associated with a reactor")
           (source-kind . "AutoLISP/ActiveX")
           (alphabetic-group . "V")
           (feature-groups . ("Reactor Functions Reference (AutoLISP/ActiveX)"))
           (supported-platforms . "Windows only")
           (signature . "(vlr-data-set obj data)")
           (arguments . (("obj" . "Type: VLR object\nA object representing the reactor object whose data is to be overwritten.")
                           ("data" . "Type: Integer, Real, String, List, VLA-object, Safearray, Variant, T, or nil\nAny AutoLISP data.")))
           (return-values . "Type: Integer, Real, String, List, VLA-object, Safearray, Variant, T, or nil\nThe data argument.")
           (release-information . nil)
           (history . nil)
           (examples . "Return the application-specific data value attached to a reactor:\n\n(vlr-data circleReactor)\n\"Circle Reactor\"\n\nReplace the text string used to identify the reactor:\n\n(vlr-data-set circleReactor \"Circle Area Reactor\")\n\"Circle Area Reactor\"\n\nVerify the change:\n\n(vlr-data circleReactor)\n\"Circle Area Reactor\"")
           (url . "https://help.autodesk.com/cloudhelp/2023/ENU/AutoCAD-AutoLISP-Reference/files/GUID-DAAADA53-0BEB-443C-A06A-97F56C4928AE.htm")
           (guid . "GUID-DAAADA53-0BEB-443C-A06A-97F56C4928AE"))))
    *autolisp-reference-parts*))

(setq *autolisp-reference-entry* nil)

(setq *autolisp-reference-value* "GUID-61F68E16-67F6-4925-BF73-5E24BB7B3DC0")

(setq *autolisp-reference-entry* (cons (cons 'guid *autolisp-reference-value*) *autolisp-reference-entry*))

(setq *autolisp-reference-value* "https://help.autodesk.com/cloudhelp/2023/ENU/AutoCAD-AutoLISP-Reference/files/GUID-61F68E16-67F6-4925-BF73-5E24BB7B3DC0.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following DeepClone reactor events:\n- DeepClone reactor events Event name Description :vlr-beginDeepClone A deep clone operation is beginning. :vlr-beginDeepCloneXlation A deep clone operation has two stages. First, each object and any owned objects are cloned. Second, any object ID references are translated to their cloned IDs. This callback occurs between these two stages. :vlr-abortDeepClone A deep clone operation is aborting. :vlr-endDeepClone A deep clone operation is ending.\n- callback_function is a symbol representing a function to be called when the event fires. Each callback function accepts two arguments:\n- reactor_object -- The VLR object that called the callback function.\n- list -- A list of extra data elements associated with the particular event. The contents")

(setq *autolisp-reference-string* (strcat *autolisp-reference-string* " of this list for particular events are shown in the “DeepClone reactor callback data” table.\n- DeepClone reactor callback data Name List length Parameters :vlr-beginDeepClone :vlr-abortDeepClone :vlr-endDeepClone 0 :vlr-beginDeepCloneXlation 1 An integer containing the return error status; if this value indicates an error, the deep clone operation is terminated"))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-deepclone-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of a deep clone event")

(setq *autolisp-reference-entry* (cons (cons 'summary *autolisp-reference-value*) *autolisp-reference-entry*))

(setq *autolisp-reference-value* "vlr-deepclone-reactor (AutoLISP/ActiveX)")

(setq *autolisp-reference-entry* (cons (cons 'title *autolisp-reference-value*) *autolisp-reference-entry*))

(setq *autolisp-reference-value* "vlr-deepclone-reactor")

(setq *autolisp-reference-entry* (cons (cons 'name *autolisp-reference-value*) *autolisp-reference-entry*))

(setq *autolisp-reference-parts* (cons (list (cons "vlr-deepclone-reactor" *autolisp-reference-entry*)) *autolisp-reference-parts*))

(setq *autolisp-reference-entry* nil)

(setq *autolisp-reference-value* "GUID-6C371938-A51E-43C8-B4A7-365A595DAB11")

(setq *autolisp-reference-entry* (cons (cons 'guid *autolisp-reference-value*) *autolisp-reference-entry*))

(setq *autolisp-reference-value* "https://help.autodesk.com/cloudhelp/2023/ENU/AutoCAD-AutoLISP-Reference/files/GUID-6C371938-A51E-43C8-B4A7-365A595DAB11.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following DocManager reactor events:\n- DocManager reactor events Event name Description :vlr-documentCreated A new document was created for a drawing (new or open). Useful for updating your per-document structures. :vlr-documentToBeDestroyed A document will be destroyed. :vlr-documentLockModeWillChange A command is about to start or finish modifying elements in the document, and is obtaining or releasing a lock on the document. :vlr-documentLockModeChangeVetoed A reactor invoked veto on itself from a :vlr-documentLockModeChanged callback. :vlr-documentLockModeChanged The lock on the document has been obtained or released. :vlr-documentBecameCurrent The current document has been changed. This does not necessarily imply that the document has been activated, because changing the")

(setq *autolisp-reference-string* (strcat *autolisp-reference-string* " current document is necessary for some operations. To obtain user input, the document must be activated as well. :vlr-documentToBeActivated A currently inactive document has just received the activate signal, implying that it is about to become the current document. :vlr-documentToBeDeactivated Another window (inside or outside of AutoCAD) has been activated.\n- callback_function is a symbol representing a function to be called when the event fires. Each callback function accepts two arguments:\n- reactor_object -- The VLR object that called the callback function.\n- list -- A list of extra data elements associated with the particular event. The contents of this list for particular events are shown in the “DocManager reactor callback data” table.\n- DocManager reactor callback data Name List length Parameters :vlr-documentCreated :vlr-documentToBeDestroyed :vlr-documentBecameCurrent :vl"))

(setq *autolisp-reference-string* (strcat *autolisp-reference-string* "r-documentToBeActivated :vlr-documentToBeDeactivated 1 The affected document object (VLA-object). :vlr-documentLockModeChangeVetoed 2 First parameter is the affected document object (VLA-object). Second parameter is the global command string passed in for the lock request. If the callback is being made on behalf of an unlock request, the string will be prefixed with “#”. :vlr-documentLockModeWillChange :vlr-documentLockModeChanged 5 First parameter is the affected document object (VLA-object). Second parameter is an integer indicating the lock currently in effect for the document object. Third parameter is an integer indicating the lock mode that will be in effect after the lock is applied. Fourth parameter is the strongest lock mode from all other execution contexts. Fifth parameter is the global command string passed in for the lock request. If the callback is being made on behalf of a"))

(setq *autolisp-reference-string* (strcat *autolisp-reference-string* "n unlock request, the string will be prefixed with “#”. Lock modes may be any of the following: 1—Auto Write Lock 2—Not Locked 4—Shared Write 8—Read 10—Exclusive Write"))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-docmanager-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs a reactor object that notifies of events relating to drawing documents")

(setq *autolisp-reference-entry* (cons (cons 'summary *autolisp-reference-value*) *autolisp-reference-entry*))

(setq *autolisp-reference-value* "vlr-docmanager-reactor (AutoLISP/ActiveX)")

(setq *autolisp-reference-entry* (cons (cons 'title *autolisp-reference-value*) *autolisp-reference-entry*))

(setq *autolisp-reference-value* "vlr-docmanager-reactor")

(setq *autolisp-reference-entry* (cons (cons 'name *autolisp-reference-value*) *autolisp-reference-entry*))

(setq *autolisp-reference-parts* (cons (list (cons "vlr-docmanager-reactor" *autolisp-reference-entry*)) *autolisp-reference-parts*))

(setq *autolisp-reference-entry* nil)

(setq *autolisp-reference-value* "GUID-82B7F0D1-02AD-4463-A8A3-BF87EFCC83A4")

(setq *autolisp-reference-entry* (cons (cons 'guid *autolisp-reference-value*) *autolisp-reference-entry*))

(setq *autolisp-reference-value* "https://help.autodesk.com/cloudhelp/2023/ENU/AutoCAD-AutoLISP-Reference/files/GUID-82B7F0D1-02AD-4463-A8A3-BF87EFCC83A4.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following DWG reactor events:\n- DWG reactor events Event name Description :vlr-beginClose The drawing database is to be closed. :vlr-databaseConstructed A drawing database has been constructed. :vlr-databaseToBeDestroyed The contents of the drawing database are about to be deleted from memory. vlr-beginDwgOpen AutoCAD is about to open a drawing file. :vlr-endDwgOpen AutoCAD has ended the open operation. :vlr-dwgFileOpened A new drawing has been loaded into the AutoCAD window. vlr-beginSave AutoCAD is about to save the drawing file. vlr-saveComplete AutoCAD has saved the current drawing to disk.\n- callback_function is a symbol representing a function to be called when the event occurs. Each callback function accepts two arguments:\n- reactor_object -- The VLR object that call")

(setq *autolisp-reference-string* (strcat *autolisp-reference-string* "ed the callback function.\n- list -- A list of extra data elements associated with the particular event. The contents of this list for particular events are shown in the “DWG reactor callback data” table.\n- DWG reactor callback data Name List length Parameters :vlr-beginClose :vlr-databaseConstructed :vlr-databaseToBeDestroyed 0 :vlr-beginDwgOpen :vlr-endDwgOpen :vlr-dwgFileOpened 1 A string identifying the file to open. :vlr-beginSave 2 First parameter is the database object to save at. Second parameter is a string containing the default file name for save, which may be changed by the user. :vlr-saveComplete 2 First parameter is the database object to save at. Second parameter is a string containing the actual file name used for the save."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-dwg-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of a drawing event (for example, opening or closing a drawing file)")

(setq *autolisp-reference-entry* (cons (cons 'summary *autolisp-reference-value*) *autolisp-reference-entry*))

(setq *autolisp-reference-value* "vlr-dwg-reactor (AutoLISP/ActiveX)")

(setq *autolisp-reference-entry* (cons (cons 'title *autolisp-reference-value*) *autolisp-reference-entry*))

(setq *autolisp-reference-value* "vlr-dwg-reactor")

(setq *autolisp-reference-entry* (cons (cons 'name *autolisp-reference-value*) *autolisp-reference-entry*))

(setq *autolisp-reference-parts* (cons (list (cons "vlr-dwg-reactor" *autolisp-reference-entry*)) *autolisp-reference-parts*))

(setq *autolisp-reference-entry* nil)

(setq *autolisp-reference-value* "GUID-EFE16A66-767A-4154-9123-DDF9BB281221")

(setq *autolisp-reference-entry* (cons (cons 'guid *autolisp-reference-value*) *autolisp-reference-entry*))

(setq *autolisp-reference-value* "https://help.autodesk.com/cloudhelp/2023/ENU/AutoCAD-AutoLISP-Reference/files/GUID-EFE16A66-767A-4154-9123-DDF9BB281221.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following DXF reactor events:\n- DXF reactor events Event name Description :vlr-beginDxfIn The contents of a DXF file are to be appended to the drawing database. :vlr-abortDxfIn The DXF import was not successful. :vlr-dxfInComplete The DXF import was successful. :vlr-beginDxfOut AutoCAD is about to export the drawing database into a DXF file. :vlr-abortDxfOut The DXF export operation failed. :vlr-dxfOutComplete The DXF export operation was successful.\n- callback_function is a symbol representing a function to be called when the event fires. Each callback function accepts two arguments:\n- reactor_object -- The VLR object that called the callback function.\n- list -- A list of extra data elements associated with the particular event. The contents of this list for particular ev")

(setq *autolisp-reference-string* (strcat *autolisp-reference-string* "ents are shown in the “DXF reactor callback data” table.\n- DXF reactor callback data Name List length :vlr-beginDxfIn :vlr-abortDxfIn :vlr-dxfInComplete, :vlr-beginDxfOut :vlr-abortDxfOut :vlr-dxfOutComplete 0"))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-dxf-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of an event related to reading or writing a DXF file")

(setq *autolisp-reference-entry* (cons (cons 'summary *autolisp-reference-value*) *autolisp-reference-entry*))

(setq *autolisp-reference-value* "vlr-dxf-reactor (AutoLISP/ActiveX)")

(setq *autolisp-reference-entry* (cons (cons 'title *autolisp-reference-value*) *autolisp-reference-entry*))

(setq *autolisp-reference-value* "vlr-dxf-reactor")

(setq *autolisp-reference-entry* (cons (cons 'name *autolisp-reference-value*) *autolisp-reference-entry*))

(setq *autolisp-reference-parts* (cons (list (cons "vlr-dxf-reactor" *autolisp-reference-entry*)) *autolisp-reference-parts*))

(setq *autolisp-reference-entry* nil)

(setq *autolisp-reference-value* "GUID-B13FF930-7063-4E25-846B-C0AC907C9943")

(setq *autolisp-reference-entry* (cons (cons 'guid *autolisp-reference-value*) *autolisp-reference-entry*))

(setq *autolisp-reference-value* "https://help.autodesk.com/cloudhelp/2023/ENU/AutoCAD-AutoLISP-Reference/files/GUID-B13FF930-7063-4E25-846B-C0AC907C9943.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Editor reactor events:\n- Editor reactor events Event name Description :vlr-beginClose The drawing database is to be closed. :vlr-beginDxfIn The contents of a DXF file are to be appended to the drawing database. :vlr-abortDxfIn The DXF import was not successful. :vlr-dxfInComplete The DXF import completed successfully. :vlr-beginDxfOut AutoCAD is about to export the drawing database into a DXF file. :vlr-abortDxfOut DXF export operation failed. :vlr-dxfOutComplete DXF export operation completed successfully. :vlr-databaseToBeDestroyed The contents of the drawing database are about to be deleted from memory. :vlr-unknownCommand A command not known to AutoCAD was issued. :vlr-commandWillStart An AutoCAD command has been called. vlr-commandEnded An AutoCAD command has c")

(setq *autolisp-reference-string* (strcat *autolisp-reference-string* "ompleted. :vlr-commandCancelled An AutoCAD command has been canceled. :vlr-commandFailed An AutoCAD command failed to complete. :vlr-lispWillStart An AutoLISP expression is to be evaluated. :vlr-lispEnded Evaluation of an AutoLISP expression has completed. :vlr-lispCancelled Evaluation of an AutoLISP expression has been canceled. :vlr-beginDwgOpen AutoCAD is about to open a drawing file. :vlr-endDwgOpen AutoCAD has ended the open operation. :vlr-dwgFileOpened A new drawing has been loaded into the AutoCAD window. :vlr-beginSave AutoCAD is about to save the drawing file. :vlr-saveComplete AutoCAD has saved the current drawing to disk. :vlr-sysVarWillChange AutoCAD is about to change the value of a system variable. :vlr-sysVarChanged The value of a system variable has changed.\n- callback_function is a symbol representing a function to be called when the event fires. Each callback function"))

(setq *autolisp-reference-string* (strcat *autolisp-reference-string* " accepts two arguments:\n- reactor_object -- The VLR object that called the callback function.\n- list -- A list of extra data elements associated with the particular event. The contents of this list for particular events are shown in the “Editor reactor callback data” table.\n- Editor reactor callback data Name List length Parameters :vlr-lispEnded :vlr-lispCancelled :vlr-beginClose :vlr-beginDxfIn :vlr-abortDxfIn :vlr-dxfInComplete :vlr-beginDxfOut :vlr-abortDxfOut :vlr-dxfOutComplete :vlr-databaseToBeDestroyed 0 :vlr-unknownCommand :vlr-commandWillStart :vlr-commandEnded :vlr-commandCancelled :vlr-commandFailed 1 A string containing the command name. :vlr-lispWillStart 1 A string containing the first line of the AutoLISP expression to evaluate. :vlr-beginDwgOpen :vlr-endDwgOpen :vlr-dwgFileOpened 1 A string identifying the file to open. :vlr-beginSave 2 First parameter is the database"))

(setq *autolisp-reference-string* (strcat *autolisp-reference-string* " object to save at. Second parameter is a string containing the default file name for save, which may be changed by the user. :vlr-saveComplete 2 First parameter is the database object to save at. Second parameter is a string containing the actual file name used for the save. :vlr-sysVarWillChange 1 A string naming the system variable. :vlr-sysVarChanged 2 First parameter is a string naming the system variable. Second parameter is an integer indicating whether the change was successful (1 = success, 0 = failed)."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-editor-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object")

(setq *autolisp-reference-entry* (cons (cons 'summary *autolisp-reference-value*) *autolisp-reference-entry*))

(setq *autolisp-reference-value* "vlr-editor-reactor (AutoLISP/ActiveX)")

(setq *autolisp-reference-entry* (cons (cons 'title *autolisp-reference-value*) *autolisp-reference-entry*))

(setq *autolisp-reference-value* "vlr-editor-reactor")

(setq *autolisp-reference-entry* (cons (cons 'name *autolisp-reference-value*) *autolisp-reference-entry*))

(setq *autolisp-reference-parts* (cons (list (cons "vlr-editor-reactor" *autolisp-reference-entry*)) *autolisp-reference-parts*))

(setq *autolisp-reference-entry* nil)

(setq *autolisp-reference-value* "GUID-387AC57D-1E15-4089-9271-8BFC7CBA5854")

(setq *autolisp-reference-entry* (cons (cons 'guid *autolisp-reference-value*) *autolisp-reference-entry*))

(setq *autolisp-reference-value* "https://help.autodesk.com/cloudhelp/2023/ENU/AutoCAD-AutoLISP-Reference/files/GUID-387AC57D-1E15-4089-9271-8BFC7CBA5854.htm")

(setq *autolisp-reference-entry* (cons (cons 'url *autolisp-reference-value*) *autolisp-reference-entry*))

(setq *autolisp-reference-value* nil)

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* nil)

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Insert reactor events:\n- Insert reactor events Event name Description :vlr-beginInsert A block is about to be inserted into the drawing database. :vlr-beginInsertM A 3D transformation matrix is about to be inserted into the drawing database. :vlr-otherInsert A block or matrix has been added to the drawing database. This notification is sent after the insert process completes copying the object into the database, but before ID translation or entity transformation occurs. :vlr-endInsert Usually indicates an insert operation on the drawing database is complete. However, in some cases, the transform has not yet happened, or the block that was created has not yet been appended. This means the objects copied are not yet graphical, and you cannot use them in selection sets")

(setq *autolisp-reference-string* (strcat *autolisp-reference-string* " until the :vlr-commandEnded notification is received. :vlr-abortInsert Insert operation was terminated and did not complete, leaving the database in an unstable state.\n- callback_function is a symbol representing a function to be called when the event fires. Each callback function accepts two arguments:\n- reactor_object -- The VLR object that called the callback function.\n- list -- A list of extra data elements associated with the particular event. The contents of this list for particular events is shown in the “Insert reactor callback data” table.\n- Insert reactor callback data Name List length Parameters :vlr-beginInsert 3 First parameter is a VLA-object pointing to the database in which the block is being inserted. Second parameter is a string naming the block to be inserted. Third parameter is a VLA-object identifying the source database of the block. :vlr-beginInsertM 3 First p"))

(setq *autolisp-reference-string* (strcat *autolisp-reference-string* "arameter is a VLA-object pointing to the database in which the 3D transformation matrix is being inserted. Second parameter is the 3D transformation matrix to be inserted. Third parameter is a VLA-object identifying the source database of the matrix. :vlr-otherInsert 2 First parameter is a VLA-object pointing to the database in which the block or matrix is being inserted. Second parameter is a VLA-object identifying the source database of the block or matrix. :vlr-endInsert :vlr-abortInsert 1 VLA-object pointing to target database."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-insert-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of an event related to block insertion")

(setq *autolisp-reference-entry* (cons (cons 'summary *autolisp-reference-value*) *autolisp-reference-entry*))

(setq *autolisp-reference-value* "vlr-insert-reactor (AutoLISP/ActiveX)")

(setq *autolisp-reference-entry* (cons (cons 'title *autolisp-reference-value*) *autolisp-reference-entry*))

(setq *autolisp-reference-value* "vlr-insert-reactor")

(setq *autolisp-reference-entry* (cons (cons 'name *autolisp-reference-value*) *autolisp-reference-entry*))

(setq *autolisp-reference-parts* (cons (list (cons "vlr-insert-reactor" *autolisp-reference-entry*)) *autolisp-reference-parts*))

(setq *autolisp-reference-entry* nil)

(setq *autolisp-reference-value* "GUID-665BA981-DABB-4120-B177-046A46C29EDE")

(setq *autolisp-reference-entry* (cons (cons 'guid *autolisp-reference-value*) *autolisp-reference-entry*))

(setq *autolisp-reference-value* "https://help.autodesk.com/cloudhelp/2023/ENU/AutoCAD-AutoLISP-Reference/files/GUID-665BA981-DABB-4120-B177-046A46C29EDE.htm")

(setq *autolisp-reference-entry* (cons (cons 'url *autolisp-reference-value*) *autolisp-reference-entry*))

(setq *autolisp-reference-value* "(vlr-linker-reactor nil\n   '((:vlr-rxAppLoaded . my-vlr-trace-reaction)))\n#<VLR-Linker-Reactor>")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Linker reactor events:\n- Linker reactor events Name Event :vlr-rxAppLoaded The dynamic linker has loaded a new ObjectARX program. The program has finished its initialization. :vlr-rxAppUnLoaded The dynamic linker has unloaded an ObjectARX program. The program already has done its clean-up.\n- callback_function is a symbol representing a function to be called when the event fires. Each callback function accepts two arguments:\n- reactor_object -- The VLR object that called the callback function.\n- list -- A list containing the name of the ObjectARX program that was loaded or unloaded (a string).")

(setq *autolisp-reference-value* (cons (cons "callbacks" *autolisp-reference-string*) *autolisp-reference-value*))

(setq *autolisp-reference-string* "Type: Integer, Real, String, List, VLA-object, Safearray, Variant, T, or nil\nAny AutoLISP data to be associated with the reactor object.")

(setq *autolisp-reference-value* (cons (cons "data" *autolisp-reference-string*) *autolisp-reference-value*))

(setq *autolisp-reference-entry* (cons (cons 'arguments *autolisp-reference-value*) *autolisp-reference-entry*))

(setq *autolisp-reference-value* "(vlr-linker-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs a reactor object that notifies your application every time an ObjectARX application is loaded or unloaded")

(setq *autolisp-reference-entry* (cons (cons 'summary *autolisp-reference-value*) *autolisp-reference-entry*))

(setq *autolisp-reference-value* "vlr-linker-reactor (AutoLISP/ActiveX)")

(setq *autolisp-reference-entry* (cons (cons 'title *autolisp-reference-value*) *autolisp-reference-entry*))

(setq *autolisp-reference-value* "vlr-linker-reactor")

(setq *autolisp-reference-entry* (cons (cons 'name *autolisp-reference-value*) *autolisp-reference-entry*))

(setq *autolisp-reference-parts* (cons (list (cons "vlr-linker-reactor" *autolisp-reference-entry*)) *autolisp-reference-parts*))

(setq *autolisp-reference-entry* nil)

(setq *autolisp-reference-value* "GUID-2EB16403-0B43-4CD4-AEFE-59CA2728A077")

(setq *autolisp-reference-entry* (cons (cons 'guid *autolisp-reference-value*) *autolisp-reference-entry*))

(setq *autolisp-reference-value* "https://help.autodesk.com/cloudhelp/2023/ENU/AutoCAD-AutoLISP-Reference/files/GUID-2EB16403-0B43-4CD4-AEFE-59CA2728A077.htm")

(setq *autolisp-reference-entry* (cons (cons 'url *autolisp-reference-value*) *autolisp-reference-entry*))

(setq *autolisp-reference-value* nil)

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* nil)

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Lisp reactor events:\n- Lisp reactor events Event name Description :vlr-lispWillStart An AutoLISP expression is to be evaluated. :vlr-lispEnded Evaluation of an AutoLISP expression has been completed. :vlr-lispCancelled Evaluation of an AutoLISP expression has been canceled.\n- callback_function is a symbol representing a function to be called when the event fires. Each callback function accepts two arguments:\n- reactor_object -- The VLR object that called the callback function.\n- list -- A list of extra data elements associated with the particular event. The contents of this list for particular events are shown in the table Lisp reactor callback data” table.\n- Lisp reactor callback data Name List length Parameters :vlr-lispEnded :vlr-lispCancelled 0 :vlr-lispWill")

(setq *autolisp-reference-string* (strcat *autolisp-reference-string* "Start 1 A string containing the first line of the AutoLISP expression to evaluate."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-lisp-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of a LISP event")

(setq *autolisp-reference-entry* (cons (cons 'summary *autolisp-reference-value*) *autolisp-reference-entry*))

(setq *autolisp-reference-value* "vlr-lisp-reactor (AutoLISP/ActiveX)")

(setq *autolisp-reference-entry* (cons (cons 'title *autolisp-reference-value*) *autolisp-reference-entry*))

(setq *autolisp-reference-value* "vlr-lisp-reactor")

(setq *autolisp-reference-entry* (cons (cons 'name *autolisp-reference-value*) *autolisp-reference-entry*))

(setq *autolisp-reference-parts* (cons (list (cons "vlr-lisp-reactor" *autolisp-reference-entry*)) *autolisp-reference-parts*))

(setq *autolisp-reference-entry* nil)

(setq *autolisp-reference-value* "GUID-3F4044CB-50AE-4869-A3FF-7DA8EB9D7A87")

(setq *autolisp-reference-entry* (cons (cons 'guid *autolisp-reference-value*) *autolisp-reference-entry*))

(setq *autolisp-reference-value* "https://help.autodesk.com/cloudhelp/2023/ENU/AutoCAD-AutoLISP-Reference/files/GUID-3F4044CB-50AE-4869-A3FF-7DA8EB9D7A87.htm")

(setq *autolisp-reference-entry* (cons (cons 'url *autolisp-reference-value*) *autolisp-reference-entry*))

(setq *autolisp-reference-value* nil)

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* nil)

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Miscellaneous reactor events:\n- Miscellaneous reactor events Event name Description :vlr-pickfirstModified The pickfirst selection set of the current document has been modified. :vlr-layoutSwitched The layout was switched.\n- callback_function is a symbol representing a function to be called when the event fires. Each callback function accepts two arguments:\n- reactor_object -- The VLR object that called the callback function.\n- list -- A list of extra data elements associated with the particular event. The contents of this list for particular events are shown in the “Miscellaneous reactor callback data” table.\n- Miscellaneous reactor callback data Name List length Parameters :vlr-pickfirstModified 0 :vlr-layoutSwitched 1 A string naming the layout switched to.")

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-miscellaneous-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that does not fall under any other editor reactor types")

(setq *autolisp-reference-entry* (cons (cons 'summary *autolisp-reference-value*) *autolisp-reference-entry*))

(setq *autolisp-reference-value* "vlr-miscellaneous-reactor (AutoLISP/ActiveX)")

(setq *autolisp-reference-entry* (cons (cons 'title *autolisp-reference-value*) *autolisp-reference-entry*))

(setq *autolisp-reference-value* "vlr-miscellaneous-reactor")

(setq *autolisp-reference-entry* (cons (cons 'name *autolisp-reference-value*) *autolisp-reference-entry*))

(setq *autolisp-reference-parts* (cons (list (cons "vlr-miscellaneous-reactor" *autolisp-reference-entry*)) *autolisp-reference-parts*))

(setq *autolisp-reference-entry* nil)

(setq *autolisp-reference-value* "GUID-31986735-3923-41B2-8EAD-6E8F05ABC5F1")

(setq *autolisp-reference-entry* (cons (cons 'guid *autolisp-reference-value*) *autolisp-reference-entry*))

(setq *autolisp-reference-value* "https://help.autodesk.com/cloudhelp/2023/ENU/AutoCAD-AutoLISP-Reference/files/GUID-31986735-3923-41B2-8EAD-6E8F05ABC5F1.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Mouse reactor events:\n- Mouse reactor events Event name Description :vlr-beginDoubleClick The user has double-clicked. :vlr-beginRightClick The user has right-clicked.\n- callback_function is a symbol representing a function to be called when the event fires. Each callback function accepts two arguments:\n- reactor_object -- The VLR object that called the callback function.\n- list -- A list of extra data elements associated with the particular event. The contents of this list for particular events are shown in the “Mouse reactor callback data” table.\n- Mouse reactor callback data Name List length Parameters :vlr-beginDoubleClick :vlr-beginRightClick 1 A 3D point list (list of 3 reals) showing the point clicked on, in WCS.")

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-mouse-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of a mouse event (for example, a double-click)")

(setq *autolisp-reference-entry* (cons (cons 'summary *autolisp-reference-value*) *autolisp-reference-entry*))

(setq *autolisp-reference-value* "vlr-mouse-reactor (AutoLISP/ActiveX)")

(setq *autolisp-reference-entry* (cons (cons 'title *autolisp-reference-value*) *autolisp-reference-entry*))

(setq *autolisp-reference-value* "vlr-mouse-reactor")

(setq *autolisp-reference-entry* (cons (cons 'name *autolisp-reference-value*) *autolisp-reference-entry*))

(setq *autolisp-reference-parts* (cons (list (cons "vlr-mouse-reactor" *autolisp-reference-entry*)) *autolisp-reference-parts*))

(setq *autolisp-reference-parts*
  (cons
    '(("vlr-notification" .
          ((name . "vlr-notification")
           (title . "vlr-notification (AutoLISP/ActiveX)")
           (summary . "Determines whether or not a reactor will fire if its associated namespace is not active")
           (source-kind . "AutoLISP/ActiveX")
           (alphabetic-group . "V")
           (feature-groups . ("Reactor Functions Reference (AutoLISP/ActiveX)"))
           (supported-platforms . "Windows only")
           (signature . "(vlr-notification reactor)")
           (arguments . (("reactor" . "Type: VLR object\nAn object.")))
           (return-values . "Type: Symbol\nA symbol, which can be either 'all-documents (the reactor fires whether or not its associated document is active), or 'active-document-only (the reactor fires only if its associated document is active).")
           (release-information . nil)
           (history . nil)
           (examples . "N/A")
           (url . "https://help.autodesk.com/cloudhelp/2023/ENU/AutoCAD-AutoLISP-Reference/files/GUID-0A10A687-C72A-407C-AD71-C9DD76084A45.htm")
           (guid . "GUID-0A10A687-C72A-407C-AD71-C9DD76084A45"))))
    *autolisp-reference-parts*))

(setq *autolisp-reference-entry* nil)

(setq *autolisp-reference-value* "GUID-310D685C-142E-4DA1-BDA1-B6E9AC5E98E8")

(setq *autolisp-reference-entry* (cons (cons 'guid *autolisp-reference-value*) *autolisp-reference-entry*))

(setq *autolisp-reference-value* "https://help.autodesk.com/cloudhelp/2023/ENU/AutoCAD-AutoLISP-Reference/files/GUID-310D685C-142E-4DA1-BDA1-B6E9AC5E98E8.htm")

(setq *autolisp-reference-entry* (cons (cons 'url *autolisp-reference-value*) *autolisp-reference-entry*))

(setq *autolisp-reference-value* "The following code attaches an object reactor to the myCircle object. It defines the reactor to respond whenever the object is modified (:vlr-modified) and to call the print-radius function in response to the modification event:\n\n(setq circleReactor (vlr-object-reactor (list myCircle)\n         \"Circle Reactor\" '((:vlr-modified . print-radius))))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Object Events:\n- Object events Name Event :vlr-cancelled The modification of the object has been canceled. :vlr-copied The object has been copied. :vlr-erased Erase-flag of the object has been set. :vlr-unerased Erase-flag of the object has been reset. :vlr-goodbye The object is about to be deleted from memory. :vlr-openedForModify The object is about to be modified. :vlr-modified The object has been modified. If the modification was canceled, also :vlr-cancelled and :vlr-modifyUndone will be fired. :vlr-subObjModified A sub-entity of the object has been modified. This event is triggered for modifications to vertices of polylines or meshes, and for attributes owned by block references. :vlr-modifyUndone The object's modification was undone. :vlr-modifiedXData The ob")

(setq *autolisp-reference-string* (strcat *autolisp-reference-string* "ject's extended entity data has been modified. :vlr-unappended The object has been detached from the drawing database. :vlr-reappended The object has been re-attached to the drawing database. :vlr-objectClosed The object's modification has been finished.\n- callback_function is a symbol representing a function to be called when the event fires. Each callback function accepts three arguments:\n- owner -- The owner of the VLA-object the event applies to.\n- reactor_object -- The VLR object that called the callback function.\n- list -- A list of extra data elements associated with the particular event. The contents of this list for particular events are shown in the “Object Events Callback Data” table.\n- Object events callback data Name List length Parameters :vlr-cancelled :vlr-erased, :vlr-unerased :vlr-goodbye :vlr-openedForModify :vlr-modified :vlr-modifyUndone :vlr-modifiedXData :vlr-"))

(setq *autolisp-reference-string* (strcat *autolisp-reference-string* "unappended :vlr-reappended :vlr-objectClosed 0 :vlr-copied 1 The object created by the copy operation (ename). :vlr-subObjModified 1 The sub-object (ename) that has been modified"))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-string* "Type: List\nAn AutoLISP list of VLA-objects identifying the drawing objects to be watched.")

(setq *autolisp-reference-value* (cons (cons "owners" *autolisp-reference-string*) *autolisp-reference-value*))

(setq *autolisp-reference-entry* (cons (cons 'arguments *autolisp-reference-value*) *autolisp-reference-entry*))

(setq *autolisp-reference-value* "(vlr-object-reactor owners data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs a drawing object reactor object")

(setq *autolisp-reference-entry* (cons (cons 'summary *autolisp-reference-value*) *autolisp-reference-entry*))

(setq *autolisp-reference-value* "vlr-object-reactor (AutoLISP/ActiveX)")

(setq *autolisp-reference-entry* (cons (cons 'title *autolisp-reference-value*) *autolisp-reference-entry*))

(setq *autolisp-reference-value* "vlr-object-reactor")

(setq *autolisp-reference-entry* (cons (cons 'name *autolisp-reference-value*) *autolisp-reference-entry*))

(setq *autolisp-reference-parts* (cons (list (cons "vlr-object-reactor" *autolisp-reference-entry*)) *autolisp-reference-parts*))

(setq *autolisp-reference-parts*
  (cons
    '(("vlr-owner-add" .
          ((name . "vlr-owner-add")
           (title . "vlr-owner-add (AutoLISP/ActiveX)")
           (summary . "Adds an object to the list of owners of an object reactor")
           (source-kind . "AutoLISP/ActiveX")
           (alphabetic-group . "V")
           (feature-groups . ("Reactor Functions Reference (AutoLISP/ActiveX)"))
           (supported-platforms . "Windows only")
           (signature . "(vlr-owner-add reactor owner)")
           (arguments . (("reactor" . "Type: VLR object\nAn object.")
                           ("owner" . "Type: VLA-object\nAn object to be added to the list of notifiers for this reactor.")))
           (return-values . "Type: VLA-object\nThe object to which the reactor has been added.")
           (release-information . nil)
           (history . nil)
           (examples . "In the following example, an arc object named “archie” is added to the owner list of reactor circleReactor:\n\n(vlr-owner-add circleReactor archie)\n#<VLA-OBJECT IAcadArc 03ad0bcc>")
           (url . "https://help.autodesk.com/cloudhelp/2023/ENU/AutoCAD-AutoLISP-Reference/files/GUID-8DF13914-E66F-410D-BFDF-8A9A1860AFBE.htm")
           (guid . "GUID-8DF13914-E66F-410D-BFDF-8A9A1860AFBE"))))
    *autolisp-reference-parts*))

(setq *autolisp-reference-parts*
  (cons
    '(("vlr-owner-remove" .
          ((name . "vlr-owner-remove")
           (title . "vlr-owner-remove (AutoLISP/ActiveX)")
           (summary . "Removes an object from the list of owners of an object reactor")
           (source-kind . "AutoLISP/ActiveX")
           (alphabetic-group . "V")
           (feature-groups . ("Reactor Functions Reference (AutoLISP/ActiveX)"))
           (supported-platforms . "Windows only")
           (signature . "(vlr-owner-remove reactor owner)")
           (arguments . (("reactor" . "Type: VLR object\nAn object.")
                           ("owner" . "Type: VLA-object\nAn object to be removed from the list of notifiers for this reactor.")))
           (return-values . "Type: VLA-object\nThe object from which the reactor was removed.")
           (release-information . nil)
           (history . nil)
           (examples . "(vlr-owner-remove circleReactor archie)\n#<VLA-OBJECT IAcadArc 03ad0bcc>")
           (url . "https://help.autodesk.com/cloudhelp/2023/ENU/AutoCAD-AutoLISP-Reference/files/GUID-EE5ABE92-4589-482A-95B3-EC52497C3C5F.htm")
           (guid . "GUID-EE5ABE92-4589-482A-95B3-EC52497C3C5F"))))
    *autolisp-reference-parts*))

(setq *autolisp-reference-parts*
  (cons
    '(("vlr-owners" .
          ((name . "vlr-owners")
           (title . "vlr-owners (AutoLISP/ActiveX)")
           (summary . "Returns the list of owners of an object reactor")
           (source-kind . "AutoLISP/ActiveX")
           (alphabetic-group . "V")
           (feature-groups . ("Reactor Functions Reference (AutoLISP/ActiveX)"))
           (supported-platforms . "Windows only")
           (signature . "(vlr-owners reactor)")
           (arguments . (("reactor" . "Type: VLR object\nAn object.")))
           (return-values . "Type: List\nA list of objects that notify the specified reactor.")
           (release-information . nil)
           (history . nil)
           (examples . "(vlr-owners circleReactor)\n(#<VLA-OBJECT IAcadCircle 01db98f4> #<VLA-OBJECT IAcadCircle 01db9724>\n#<VLA-OBJECT IAcadCircle 01db93d4> #<VLA-OBJECT IAcadCircle 01db9084>)")
           (url . "https://help.autodesk.com/cloudhelp/2023/ENU/AutoCAD-AutoLISP-Reference/files/GUID-AD8525AF-411C-4002-A025-CD36CD59D760.htm")
           (guid . "GUID-AD8525AF-411C-4002-A025-CD36CD59D760"))))
    *autolisp-reference-parts*))

(setq *autolisp-reference-parts*
  (cons
    '(("vlr-pers" .
          ((name . "vlr-pers")
           (title . "vlr-pers (AutoLISP/ActiveX)")
           (summary . "Makes a reactor persistent")
           (source-kind . "AutoLISP/ActiveX")
           (alphabetic-group . "V")
           (feature-groups . ("Reactor Functions Reference (AutoLISP/ActiveX)"))
           (supported-platforms . "Windows only")
           (signature . "(vlr-pers reactor)")
           (arguments . (("reactor" . "Type: VLR object\nAn object.")))
           (return-values . "Type: VLR object or nil\nThe specified reactor object, if successful; otherwise nil.")
           (release-information . nil)
           (history . nil)
           (examples . "Define a reactor:\n\n(setq circleReactor (vlr-object-reactor\n  (list myCircle) \"Radius size\" '((:vlr-modified . print-radius))))\n#<VLR-Object-Reactor>\n\nMake the reactor persistent:\n\n(vlr-pers circleReactor)\n#<VLR-Object-Reactor>")
           (url . "https://help.autodesk.com/cloudhelp/2023/ENU/AutoCAD-AutoLISP-Reference/files/GUID-0F0F7B01-2CE7-4F3C-B686-B255866C9CED.htm")
           (guid . "GUID-0F0F7B01-2CE7-4F3C-B686-B255866C9CED"))))
    *autolisp-reference-parts*))

(setq *autolisp-reference-parts*
  (cons
    '(("vlr-pers-list" .
          ((name . "vlr-pers-list")
           (title . "vlr-pers-list (AutoLISP/ActiveX)")
           (summary . "Returns a list of persistent reactors in the current drawing document")
           (source-kind . "AutoLISP/ActiveX")
           (alphabetic-group . "V")
           (feature-groups . ("Reactor Functions Reference (AutoLISP/ActiveX)"))
           (supported-platforms . "Windows only")
           (signature . "(vlr-pers-list [reactor])")
           (arguments . (("reactor" . "Type: VLR object\nThe reactor object to be listed. If reactor is not specified, vlr-pers-list lists all persistent reactors.")))
           (return-values . "Type: List\nA list of reactor objects.")
           (release-information . nil)
           (history . nil)
           (examples . "(vlr-pers-list)\n(#<VLR-Object-Reactor> #<VLR-Object-Reactor> (#<VLR-Object-Reactor>)")
           (url . "https://help.autodesk.com/cloudhelp/2023/ENU/AutoCAD-AutoLISP-Reference/files/GUID-0C7564C7-1C8B-4F17-A5F8-374C2860E117.htm")
           (guid . "GUID-0C7564C7-1C8B-4F17-A5F8-374C2860E117"))))
    *autolisp-reference-parts*))

(setq *autolisp-reference-parts*
  (cons
    '(("vlr-pers-p" .
          ((name . "vlr-pers-p")
           (title . "vlr-pers-p (AutoLISP/ActiveX)")
           (summary . "Determines whether a reactor is persistent")
           (source-kind . "AutoLISP/ActiveX")
           (alphabetic-group . "V")
           (feature-groups . ("Reactor Functions Reference (AutoLISP/ActiveX)"))
           (supported-platforms . "Windows only")
           (signature . "(vlr-pers-p reactor)")
           (arguments . (("reactor" . "Type: VLR object\nAn object.")))
           (return-values . "Type: VLR object or nil\nThe specified reactor object, if it is persistent; nil, if the reactor is transient.")
           (release-information . nil)
           (history . nil)
           (examples . "Make a reactor persistent:\n\n(vlr-pers circleReactor)\n#<VLR-Object-Reactor>\n\nVerify that a reactor is persistent:\n\n(vlr-pers-p circleReactor)\n#<VLR-Object-Reactor>\n\nChange the persistent reactor to transient:\n\n(vlr-pers-release circleReactor)\n#<VLR-Object-Reactor>\n\nVerify that the reactor is no longer persistent:\n\n(vlr-pers-p circleReactor)\nnil")
           (url . "https://help.autodesk.com/cloudhelp/2023/ENU/AutoCAD-AutoLISP-Reference/files/GUID-4C03EA1B-E274-49B2-8DEE-EBCCCEE2E19E.htm")
           (guid . "GUID-4C03EA1B-E274-49B2-8DEE-EBCCCEE2E19E"))))
    *autolisp-reference-parts*))

(setq *autolisp-reference-parts*
  (cons
    '(("vlr-pers-release" .
          ((name . "vlr-pers-release")
           (title . "vlr-pers-release (AutoLISP/ActiveX)")
           (summary . "Makes a reactor transient")
           (source-kind . "AutoLISP/ActiveX")
           (alphabetic-group . "V")
           (feature-groups . ("Reactor Functions Reference (AutoLISP/ActiveX)"))
           (supported-platforms . "Windows only")
           (signature . "(vlr-pers-release reactor)")
           (arguments . (("reactor" . "Type: VLR object\nAn object.")))
           (return-values . "Type: VLR object or nil\nThe specified reactor object, if successful; otherwise nil.")
           (release-information . nil)
           (history . nil)
           (examples . "N/A")
           (url . "https://help.autodesk.com/cloudhelp/2023/ENU/AutoCAD-AutoLISP-Reference/files/GUID-79BE8AC1-4C54-49AD-B13D-CC12E06EF512.htm")
           (guid . "GUID-79BE8AC1-4C54-49AD-B13D-CC12E06EF512"))))
    *autolisp-reference-parts*))

(setq *autolisp-reference-parts*
  (cons
    '(("vlr-reaction-names" .
          ((name . "vlr-reaction-names")
           (title . "vlr-reaction-name (AutoLISP/ActiveX)")
           (summary . "Returns a list of all possible callback conditions for this reactor type")
           (source-kind . "AutoLISP/ActiveX")
           (alphabetic-group . "V")
           (feature-groups . ("Reactor Functions Reference (AutoLISP/ActiveX)"))
           (supported-platforms . "Windows only")
           (signature . "(vlr-reaction-names reactor-type)")
           (arguments . (("reactor-type" . "Type: Symbol\nOne of the following:\n- :VLR-AcDb-Reactor\n- :VLR-Command-Reactor\n- :VLR-DeepClone-Reactor\n- :VLR-DocManager-Reactor\n- :VLR-DWG-Reactor\n- :VLR-DXF-Reactor\n- :VLR-Editor-Reactor\n- :VLR-Insert-Reactor\n- :VLR-Linker-Reactor\n- :VLR-Lisp-Reactor\n- :VLR-Miscellaneous-Reactor\n- :VLR-Mouse-Reactor\n- :VLR-Object-Reactor\n- :VLR-SysVar-Reactor\n- :VLR-Toolbar-Reactor\n- :VLR-Undo-Reactor\n- :VLR-Wblock-Reactor\n- :VLR-Window-Reactor\n- :VLR-XREF-Reactor")))
           (return-values . "Type: List\nA list of symbols indicating the possible events for the specified reactor type.")
           (release-information . nil)
           (history . nil)
           (examples . "(vlr-reaction-names :VLR-Editor-Reactor)\n(:vlr-unknownCommand :vlr-commandWillStart :vlr-commandEnded....")
           (url . "https://help.autodesk.com/cloudhelp/2023/ENU/AutoCAD-AutoLISP-Reference/files/GUID-8F887EB6-81A1-4FC3-888E-1ABA00C955DF.htm")
           (guid . "GUID-8F887EB6-81A1-4FC3-888E-1ABA00C955DF"))))
    *autolisp-reference-parts*))

(setq *autolisp-reference-parts*
  (cons
    '(("vlr-reaction-set" .
          ((name . "vlr-reaction-set")
           (title . "vlr-reaction-set (AutoLISP/ActiveX)")
           (summary . "Adds or replaces a callback function in a reactor")
           (source-kind . "AutoLISP/ActiveX")
           (alphabetic-group . "V")
           (feature-groups . ("Reactor Functions Reference (AutoLISP/ActiveX)"))
           (supported-platforms . "Windows only")
           (signature . "(vlr-reaction-set reactor event function)")
           (arguments . (("reactor" . "Type: VLR object\nAn object.")
                           ("event" . "Type: Symbol\nA symbol denoting one of the event types available for this reactor type.")
                           ("function" . "Type: Symbol\nA symbol representing the AutoLISP function to be added or replaced.")))
           (return-values . "Type: Symbol\nThe value of the function argument.")
           (release-information . nil)
           (history . nil)
           (examples . "The following command changes the circleReactor reactor to call the print-area function when an object is modified:\n\n(vlr-reaction-set circleReactor :vlr-modified 'print-area)\nPRINT-AREA")
           (url . "https://help.autodesk.com/cloudhelp/2023/ENU/AutoCAD-AutoLISP-Reference/files/GUID-015B924D-3537-4215-AB24-B8A51E3F315D.htm")
           (guid . "GUID-015B924D-3537-4215-AB24-B8A51E3F315D"))))
    *autolisp-reference-parts*))

(setq *autolisp-reference-parts*
  (cons
    '(("vlr-reactions" .
          ((name . "vlr-reactions")
           (title . "vlr-reactions (AutoLISP/ActiveX)")
           (summary . "Returns a list of pairs (event-name . callback_function) for the reactor")
           (source-kind . "AutoLISP/ActiveX")
           (alphabetic-group . "V")
           (feature-groups . ("Reactor Functions Reference (AutoLISP/ActiveX)"))
           (supported-platforms . "Windows only")
           (signature . "(vlr-reactions reactor)")
           (arguments . (("reactor" . "Type: VLR object\nAn object.")))
           (return-values . "Type: List\nList that contains the name of the event and callback function for the reactor object.")
           (release-information . nil)
           (history . nil)
           (examples . "(vlr-reactions circleReactor)\n((:vlr-modified . PRINT-RADIUS))")
           (url . "https://help.autodesk.com/cloudhelp/2023/ENU/AutoCAD-AutoLISP-Reference/files/GUID-FB3EC778-96B9-4EB4-AB36-FB427E74D263.htm")
           (guid . "GUID-FB3EC778-96B9-4EB4-AB36-FB427E74D263"))))
    *autolisp-reference-parts*))

(setq *autolisp-reference-entry* nil)

(setq *autolisp-reference-value* "GUID-21785A41-7A96-40EE-89B1-17BCDBD0E903")

(setq *autolisp-reference-entry* (cons (cons 'guid *autolisp-reference-value*) *autolisp-reference-entry*))

(setq *autolisp-reference-value* "https://help.autodesk.com/cloudhelp/2023/ENU/AutoCAD-AutoLISP-Reference/files/GUID-21785A41-7A96-40EE-89B1-17BCDBD0E903.htm")

(setq *autolisp-reference-entry* (cons (cons 'url *autolisp-reference-value*) *autolisp-reference-entry*))

(setq *autolisp-reference-value* "List all reactors in a drawing:\n\n(vlr-reactors)\n((:VLR-Object-Reactor #<VLR-Object-Reactor>) (:VLR-Editor-Reactor #<VLR-Editor-Reactor>))\n\nList all object reactors:\n\n(vlr-reactors :vlr-object-reactor)\n((:VLR-Object-Reactor #<VLR-Object-Reactor>))\n\nvlr-reactors returns a list containing a single reactor list.\n\nList all database reactors:\n\n(vlr-reactors :vlr-acdb-reactor)\nnil\n\nThere are no database reactors defined.\n\nList all DWG reactors:\n\n(vlr-reactors :vlr-dwg-reactor)\n((:VLR-DWG-Reactor #<VLR-DWG-Reactor> #<VLR-DWG-Reactor>))\n\nvlr-reactors returns a list containing a list of DWG reactors.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nA list of reactor lists; otherwise nil, if there are no reactors of any specified type. Each reactor list begins with a symbol identifying the reactor type, followed by pointers to each reactor of that type.")

(setq *autolisp-reference-entry* (cons (cons 'return-values *autolisp-reference-value*) *autolisp-reference-entry*))

(setq *autolisp-reference-value* nil)

(setq *autolisp-reference-string* "Type: Symbol\nOne or more of the following:\n- :VLR-AcDb-Reactor\n- :VLR-Command-Reactor\n- :VLR-DeepClone-Reactor\n- :VLR-DocManager-Reactor\n- :VLR-DWG-Reactor\n- :VLR-DXF-Reactor\n- :VLR-Editor-Reactor\n- :VLR-Insert-Reactor\n- :VLR-Linker-Reactor\n- :VLR-Lisp-Reactor\n- :VLR-Miscellaneous-Reactor\n- :VLR-Mouse-Reactor\n- :VLR-Object-Reactor\n- :VLR-SysVar-Reactor\n- :VLR-Toolbar-Reactor\n- :VLR-Undo-Reactor\n- :VLR-Wblock-Reactor\n- :VLR-Window-Reactor\n- :VLR-XREF-Reactor")

(setq *autolisp-reference-value* (cons (cons "reactor-type" *autolisp-reference-string*) *autolisp-reference-value*))

(setq *autolisp-reference-entry* (cons (cons 'arguments *autolisp-reference-value*) *autolisp-reference-entry*))

(setq *autolisp-reference-value* "(vlr-reactors [reactor-type...])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Returns a list of existing reactors")

(setq *autolisp-reference-entry* (cons (cons 'summary *autolisp-reference-value*) *autolisp-reference-entry*))

(setq *autolisp-reference-value* "vlr-reactors (AutoLISP/ActiveX)")

(setq *autolisp-reference-entry* (cons (cons 'title *autolisp-reference-value*) *autolisp-reference-entry*))

(setq *autolisp-reference-value* "vlr-reactors")

(setq *autolisp-reference-entry* (cons (cons 'name *autolisp-reference-value*) *autolisp-reference-entry*))

(setq *autolisp-reference-parts* (cons (list (cons "vlr-reactors" *autolisp-reference-entry*)) *autolisp-reference-parts*))

(setq *autolisp-reference-parts*
  (cons
    '(("vlr-remove" .
          ((name . "vlr-remove")
           (title . "vlr-remove (AutoLISP/ActiveX)")
           (summary . "Disables a reactor")
           (source-kind . "AutoLISP/ActiveX")
           (alphabetic-group . "V")
           (feature-groups . ("Reactor Functions Reference (AutoLISP/ActiveX)"))
           (supported-platforms . "Windows only")
           (signature . "(vlr-remove reactor)")
           (arguments . (("reactor" . "Type: VLR object\nAn object.")))
           (return-values . "Type: VLR object or nil\nThe reactor argument; otherwise nil, if unsuccessful.")
           (release-information . nil)
           (history . nil)
           (examples . "The following command disables the circleReactor reactor:\n\n(vlr-remove circleReactor)\n#<VLR-Object-reactor>")
           (url . "https://help.autodesk.com/cloudhelp/2023/ENU/AutoCAD-AutoLISP-Reference/files/GUID-2580A278-39B4-4BBA-99B4-20DA9565DCCD.htm")
           (guid . "GUID-2580A278-39B4-4BBA-99B4-20DA9565DCCD"))))
    *autolisp-reference-parts*))

(setq *autolisp-reference-entry* nil)

(setq *autolisp-reference-value* "GUID-3F8E47F1-4B6C-4C59-99C1-8601953D1F2F")

(setq *autolisp-reference-entry* (cons (cons 'guid *autolisp-reference-value*) *autolisp-reference-entry*))

(setq *autolisp-reference-value* "https://help.autodesk.com/cloudhelp/2023/ENU/AutoCAD-AutoLISP-Reference/files/GUID-3F8E47F1-4B6C-4C59-99C1-8601953D1F2F.htm")

(setq *autolisp-reference-entry* (cons (cons 'url *autolisp-reference-value*) *autolisp-reference-entry*))

(setq *autolisp-reference-value* "The following function call disables all editor reactors:\n\n(vlr-remove-all :vlr-editor-reactor)\n((:VLR-Editor-Reactor #<VLR-Editor-Reactor>))\n\nThe following call disables all reactors:\n\n(vlr-remove-all)\n((:VLR-Object-Reactor #<VLR-Object-Reactor> #<VLR-Object-Reactor>\n#<VLR-Object-Reactor>)(:VLR-Editor-Reactor#<VLR-Editor-Reactor>))")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nA list of lists. The first element of each list identifies the type of reactor, and the remaining elements identify the disabled reactor objects. The function returns nil if there are no reactors active.")

(setq *autolisp-reference-entry* (cons (cons 'return-values *autolisp-reference-value*) *autolisp-reference-entry*))

(setq *autolisp-reference-value* nil)

(setq *autolisp-reference-string* "Type: Symbol\nOne of the following:\n- :VLR-AcDb-Reactor\n- :VLR-Command-Reactor\n- :VLR-DeepClone-Reactor\n- :VLR-DocManager-Reactor\n- :VLR-DWG-Reactor\n- :VLR-DXF-Reactor\n- :VLR-Editor-Reactor\n- :VLR-Insert-Reactor\n- :VLR-Linker-Reactor\n- :VLR-Lisp-Reactor\n- :VLR-Miscellaneous-Reactor\n- :VLR-Mouse-Reactor\n- :VLR-Object-Reactor\n- :VLR-SysVar-Reactor\n- :VLR-Toolbar-Reactor\n- :VLR-Undo-Reactor\n- :VLR-Wblock-Reactor\n- :VLR-Window-Reactor\n- :VLR-XREF-Reactor\nIf no reactor-type is specified, vlr-remove-all disables all reactors.")

(setq *autolisp-reference-value* (cons (cons "reactor-type" *autolisp-reference-string*) *autolisp-reference-value*))

(setq *autolisp-reference-entry* (cons (cons 'arguments *autolisp-reference-value*) *autolisp-reference-entry*))

(setq *autolisp-reference-value* "(vlr-remove-all [reactor-type])")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Disables all reactors of the specified type")

(setq *autolisp-reference-entry* (cons (cons 'summary *autolisp-reference-value*) *autolisp-reference-entry*))

(setq *autolisp-reference-value* "vlr-remove-all (AutoLISP/ActiveX)")

(setq *autolisp-reference-entry* (cons (cons 'title *autolisp-reference-value*) *autolisp-reference-entry*))

(setq *autolisp-reference-value* "vlr-remove-all")

(setq *autolisp-reference-entry* (cons (cons 'name *autolisp-reference-value*) *autolisp-reference-entry*))

(setq *autolisp-reference-parts* (cons (list (cons "vlr-remove-all" *autolisp-reference-entry*)) *autolisp-reference-parts*))

(setq *autolisp-reference-parts*
  (cons
    '(("vlr-set-notification" .
          ((name . "vlr-set-notification")
           (title . "vlr-set-notification (AutoLISP/ActiveX)")
           (summary . "Defines whether a reactor's callback function will execute if its associated namespace is not active")
           (source-kind . "AutoLISP/ActiveX")
           (alphabetic-group . "V")
           (feature-groups . ("Reactor Functions Reference (AutoLISP/ActiveX)"))
           (supported-platforms . "Windows only")
           (signature . "(vlr-set-notification reactor 'range)")
           (arguments . (("reactor" . "Type: VLR object\nAn object.")
                           ("'range" . "Type: Symbol\nThe range argument is a symbol that can be either 'all-documents (execute the callback regardless of whether the reactor is associated with the active document), or 'active-document-only (execute the callback only if the reactor is associated with the active document).")))
           (return-values . "Type: VLR object\nA reactor object.")
           (release-information . nil)
           (history . nil)
           (examples . "Set a reactor to execute its callback function even if its associated namespace is not active:\n\n(vlr-set-notification circleReactor 'all-documents)\n#<VLR-Object-Reactor>")
           (url . "https://help.autodesk.com/cloudhelp/2023/ENU/AutoCAD-AutoLISP-Reference/files/GUID-1EBB6848-E863-4067-8A61-69ED78C96F40.htm")
           (guid . "GUID-1EBB6848-E863-4067-8A61-69ED78C96F40"))))
    *autolisp-reference-parts*))

(setq *autolisp-reference-entry* nil)

(setq *autolisp-reference-value* "GUID-5AD894AB-6D29-4362-B465-018BE9F921DE")

(setq *autolisp-reference-entry* (cons (cons 'guid *autolisp-reference-value*) *autolisp-reference-entry*))

(setq *autolisp-reference-value* "https://help.autodesk.com/cloudhelp/2023/ENU/AutoCAD-AutoLISP-Reference/files/GUID-5AD894AB-6D29-4362-B465-018BE9F921DE.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following SysVar reactor events:\n- SysVar reactor events Event name Description :vlr-sysVarWillChange AutoCAD is about to change the value of a system variable. :vlr-sysVarChanged The value of a system variable has changed.\n- callback_function is a symbol representing a function to be called when the event fires. Each callback function accepts two arguments:\n- reactor_object -- The VLR object that called the callback function.\n- list -- A list of extra data elements associated with the particular event. The contents of this list for particular events are shown in the “SysVar reactor callback data” table.\n- SysVar reactor callback data Name List length Parameters :vlr-sysVarWillChange 1 A string identifying the system variable name. :vlr-sysVarChanged 2 First parameter is ")

(setq *autolisp-reference-string* (strcat *autolisp-reference-string* "a string identifying the system variable name. Second parameter is symbol indicating whether the change was successful (T if successful, nil if not)."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-sysvar-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of a change to a system variable")

(setq *autolisp-reference-entry* (cons (cons 'summary *autolisp-reference-value*) *autolisp-reference-entry*))

(setq *autolisp-reference-value* "vlr-sysvar-reactor (AutoLISP/ActiveX)")

(setq *autolisp-reference-entry* (cons (cons 'title *autolisp-reference-value*) *autolisp-reference-entry*))

(setq *autolisp-reference-value* "vlr-sysvar-reactor")

(setq *autolisp-reference-entry* (cons (cons 'name *autolisp-reference-value*) *autolisp-reference-entry*))

(setq *autolisp-reference-parts* (cons (list (cons "vlr-sysvar-reactor" *autolisp-reference-entry*)) *autolisp-reference-parts*))

(setq *autolisp-reference-entry* nil)

(setq *autolisp-reference-value* "GUID-ABCA865A-DFBE-4057-BE9E-EF465161ABCB")

(setq *autolisp-reference-entry* (cons (cons 'guid *autolisp-reference-value*) *autolisp-reference-entry*))

(setq *autolisp-reference-value* "https://help.autodesk.com/cloudhelp/2023/ENU/AutoCAD-AutoLISP-Reference/files/GUID-ABCA865A-DFBE-4057-BE9E-EF465161ABCB.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Toolbar reactor events:\n- Toolbar reactor events Event name Description :vlr-toolbarBitmapSizeWillChange The size of the AutoCAD toolbar icons is about to change. :vlr-toolbarBitmapSizeChanged The size of the AutoCAD toolbar icons has changed.\n- callback_function is a symbol representing a function to be called when the event fires. Each callback function accepts two arguments:\n- reactor_object -- The VLR object that called the callback function.\n- list -- A list of extra data elements associated with the particular event. The contents of this list for particular events are shown in the “Toolbar reactor callback data” table.\n- Toolbar reactor callback data Name List length Parameters :vlr-toolbarBitmapSizeWillChange :vlr-toolbarBitmapSizeChanged 1 T, if the tool")

(setq *autolisp-reference-string* (strcat *autolisp-reference-string* "bar is being set to large bitmaps; nil if the toolbar is being set to small bitmaps."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-toolbar-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of a change to the bitmaps in a toolbar")

(setq *autolisp-reference-entry* (cons (cons 'summary *autolisp-reference-value*) *autolisp-reference-entry*))

(setq *autolisp-reference-value* "vlr-toolbar-reactor (AutoLISP/ActiveX)")

(setq *autolisp-reference-entry* (cons (cons 'title *autolisp-reference-value*) *autolisp-reference-entry*))

(setq *autolisp-reference-value* "vlr-toolbar-reactor")

(setq *autolisp-reference-entry* (cons (cons 'name *autolisp-reference-value*) *autolisp-reference-entry*))

(setq *autolisp-reference-parts* (cons (list (cons "vlr-toolbar-reactor" *autolisp-reference-entry*)) *autolisp-reference-parts*))

(setq *autolisp-reference-parts*
  (cons
    '(("vlr-trace-reaction" .
          ((name . "vlr-trace-reaction")
           (title . "vlr-trace-reaction (AutoLISP/ActiveX)")
           (summary . "A predefined callback function that prints one or more callback arguments in the Trace window")
           (source-kind . "AutoLISP/ActiveX")
           (alphabetic-group . "V")
           (feature-groups . ("Reactor Functions Reference (AutoLISP/ActiveX)"))
           (supported-platforms . "Windows only")
           (signature . "(vlr-trace-reaction)")
           (arguments . nil)
           (return-values . "Type: nil\nAlways returns nil. A message displays the type of trigger event, the reactor type, and the command that triggered the reactor.")
           (release-information . nil)
           (history . nil)
           (examples . "Define a command reactor and assign vlr-trace-reaction as the callback function:\n\n(VLR-Reaction-Set (VLR-Command-Reactor) :VLR-commandWillStart 'VLR-trace-reaction)\nVLR-trace-reaction\n\nAt the AutoCAD Command prompt, enter the following:\n\n_.LINE\n\nRespond to the command prompts, then activate the Visual LISP window and open the Trace window. You should see the following in the Trace window:\n\n; \"Reaction\": :VLR-commandWillStart; \"argument list\": (#<VLR-COMMAND-REACTOR> (\"LINE\"))\n\nThe output from vlr-trace-reaction identifies the type of trigger event, the reactor type, and the command that triggered the reactor.")
           (url . "https://help.autodesk.com/cloudhelp/2023/ENU/AutoCAD-AutoLISP-Reference/files/GUID-489E0189-FCB3-4B6C-95F7-BEFCA4761BDF.htm")
           (guid . "GUID-489E0189-FCB3-4B6C-95F7-BEFCA4761BDF"))))
    *autolisp-reference-parts*))

(setq *autolisp-reference-parts*
  (cons
    '(("vlr-type" .
          ((name . "vlr-type")
           (title . "vlr-type (AutoLISP/ActiveX)")
           (summary . "Returns a symbol representing the reactor type")
           (source-kind . "AutoLISP/ActiveX")
           (alphabetic-group . "V")
           (feature-groups . ("Reactor Functions Reference (AutoLISP/ActiveX)"))
           (supported-platforms . "Windows only")
           (signature . "(vlr-type reactor)")
           (arguments . (("reactor" . "Type: VLR object\nAn object.")))
           (return-values . "Type: Symbol\nReactor type from the following table:")
           (release-information . nil)
           (history . nil)
           (examples . "(vlr-type circleReactor)\n:VLR-Object-Reactor")
           (url . "https://help.autodesk.com/cloudhelp/2023/ENU/AutoCAD-AutoLISP-Reference/files/GUID-214E70E6-A8F9-43F0-ABA4-2C0BAC06E0A9.htm")
           (guid . "GUID-214E70E6-A8F9-43F0-ABA4-2C0BAC06E0A9"))))
    *autolisp-reference-parts*))

(setq *autolisp-reference-parts*
  (cons
    '(("vlr-types" .
          ((name . "vlr-types")
           (title . "vlr-types (AutoLISP/ActiveX)")
           (summary . "Returns a list of all reactor types")
           (source-kind . "AutoLISP/ActiveX")
           (alphabetic-group . "V")
           (feature-groups . ("Reactor Functions Reference (AutoLISP/ActiveX)"))
           (supported-platforms . "Windows only")
           (signature . "(vlr-types)")
           (arguments . nil)
           (return-values . "Type: List\nList of available reactor types.")
           (release-information . nil)
           (history . nil)
           (examples . "(vlr-types)\n(:VLR-Linker-Reactor :VLR-Editor-Reactor :VLR-AcDb-Reactor ....)")
           (url . "https://help.autodesk.com/cloudhelp/2023/ENU/AutoCAD-AutoLISP-Reference/files/GUID-BE2619CF-8607-4E3F-B33F-A164A4CCD804.htm")
           (guid . "GUID-BE2619CF-8607-4E3F-B33F-A164A4CCD804"))))
    *autolisp-reference-parts*))

(setq *autolisp-reference-entry* nil)

(setq *autolisp-reference-value* "GUID-184F011B-8B61-4D3F-82F3-06A75C4459AE")

(setq *autolisp-reference-entry* (cons (cons 'guid *autolisp-reference-value*) *autolisp-reference-entry*))

(setq *autolisp-reference-value* "https://help.autodesk.com/cloudhelp/2023/ENU/AutoCAD-AutoLISP-Reference/files/GUID-184F011B-8B61-4D3F-82F3-06A75C4459AE.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Undo reactor events:\n- Undo reactor events Event name Description :vlr-undoSubcommandAuto The UNDO command's Auto option has been executed. :vlr-undoSubcommandControl The UNDO command's Control option has been executed. :vlr-undoSubcommandBegin The UNDO command's BEGIN or GROUP option is being performed. BEGIN and GROUP mark the beginning of a series of commands that can be undone as one unit. :vlr-undoSubcommandEnd The UNDO command's END option is being performed. UNDO/END marks the end of a series of commands that can be undone as one unit. :vlr-undoSubcommandMark The UNDO command's MARK option is about to be executed. This places a marker in the undo file so UNDO/BACK can undo back to the marker. :vlr-undoSubcommandBack The UNDO command's BACK option is about to ")

(setq *autolisp-reference-string* (strcat *autolisp-reference-string* "be performed. UNDO/BACK undoes everything back to the most recent MARK marker or back to the beginning of the undo file if no MARK marker exists. :vlr-undoSubcommandNumber The UNDO command's NUMBER option is about to be executed (the default action of the UNDO command).\n- and callback_function is a symbol representing a function to be called when the event fires. Each callback function accepts two arguments:\n- reactor_object -- The VLR object that called the callback function.\n- list -- A list of extra data elements associated with the particular event. The contents of this list for particular events are shown in the “Undo reactor callback data” table.\n- Undo reactor callback data Name List length Parameters :vlr-undoSubcommandAuto 2 First parameter is an integer indicating the activity. The value is always 4, indicating that notification occurred after the operation was performed. S"))

(setq *autolisp-reference-string* (strcat *autolisp-reference-string* "econd parameter is a symbol indicating the state of Auto mode. Value is T if Auto mode is turned on, nil if Auto mode is turned off. :vlr-undoSubcommandControl 2 First parameter is an integer indicating the activity. The value is always 4, indicating that notification occurred after the operation was performed. Second parameter is an integer indicating the Control option selected. This can be one of the following: 0 -- NONE was selected 1 -- ONE was selected 2 -- ALL was selected :vlr-undoSubcommandBegin :vlr-undoSubcommandEnd :vlr-undoSubcommandMark :vlr-undoSubcommandBack 1 An integer value of 0, indicating that notification occurs before the actual operation is performed. :vlr-undoSubcommandNumber 2 First parameter is an integer indicating the activity. The value is always 0, indicating that notification occurs before the actual operation is performed. Second parameter is an integer i"))

(setq *autolisp-reference-string* (strcat *autolisp-reference-string* "ndicating the number of steps being undone."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-undo-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of an undo event")

(setq *autolisp-reference-entry* (cons (cons 'summary *autolisp-reference-value*) *autolisp-reference-entry*))

(setq *autolisp-reference-value* "vlr-undo-reactor (AutoLISP/ActiveX)")

(setq *autolisp-reference-entry* (cons (cons 'title *autolisp-reference-value*) *autolisp-reference-entry*))

(setq *autolisp-reference-value* "vlr-undo-reactor")

(setq *autolisp-reference-entry* (cons (cons 'name *autolisp-reference-value*) *autolisp-reference-entry*))

(setq *autolisp-reference-parts* (cons (list (cons "vlr-undo-reactor" *autolisp-reference-entry*)) *autolisp-reference-parts*))

(setq *autolisp-reference-entry* nil)

(setq *autolisp-reference-value* "GUID-7A770837-376B-4F4A-A10C-D3B253546AAB")

(setq *autolisp-reference-entry* (cons (cons 'guid *autolisp-reference-value*) *autolisp-reference-entry*))

(setq *autolisp-reference-value* "https://help.autodesk.com/cloudhelp/2023/ENU/AutoCAD-AutoLISP-Reference/files/GUID-7A770837-376B-4F4A-A10C-D3B253546AAB.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Wblock reactor events:\n- Wblock reactor events Event name Description :VLR-wblockNotice A wblock operation is about to start. :VLR-beginWblockPt A wblock operation is being performed on a set of entities. :VLR-beginWblockId A wblock operation is being performed on a specified block. :VLR-beginWblock A wblock operation is being performed on an entire database. Notification does not occur until all the entities in the source database's model space are copied into the target database. :VLR-endWblock A wblock operation completed successfully. :VLR-beginWblockObjects wblock has just initialized the object ID translation map.\n- callback_function is a symbol representing a function to be called when the event fires. Each callback function accepts two arguments:\n- reactor")

(setq *autolisp-reference-string* (strcat *autolisp-reference-string* "_object -- The VLR object that called the callback function.\n- list -- A list of extra data elements associated with the particular event. The contents of this list for particular events are shown in the “Wblock reactor callback data” table.\n- Wblock reactor callback data Name List length Parameters :VLR-wblockNotice 1 Database object (VLA-object) from which the block will be created. :VLR-beginWblockPt 3 First parameter is the target database object (VLA-object). Second parameter is the source database object (VLA-object) containing the objects being wblocked. Third parameter is a 3D point list (in WCS) to be used as the base point in the target database. :VLR-beginWblockId 3 First parameter is the target database object (VLA-object). Second parameter is the source database object (VLA-object) containing the objects being wblocked. Third parameter is the object ID of the BlockTableRec"))

(setq *autolisp-reference-string* (strcat *autolisp-reference-string* "ord being wblocked. :VLR-beginWblock :VLR-otherWblock 2 First parameter is the target database object (VLA-object). Second parameter is the source database object (VLA-object) containing the objects being wblocked. :VLR-abortWblock :VLR-endWblock 1 The target database object (VLA-object). :VLR-beginWblockObjects 2 First parameter is the source database object (VLA-object) containing the objects being wblocked. Second parameter is an ID map."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-wblock-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of an event related to writing a block")

(setq *autolisp-reference-entry* (cons (cons 'summary *autolisp-reference-value*) *autolisp-reference-entry*))

(setq *autolisp-reference-value* "vlr-wblock-reactor (AutoLISP/ActiveX)")

(setq *autolisp-reference-entry* (cons (cons 'title *autolisp-reference-value*) *autolisp-reference-entry*))

(setq *autolisp-reference-value* "vlr-wblock-reactor")

(setq *autolisp-reference-entry* (cons (cons 'name *autolisp-reference-value*) *autolisp-reference-entry*))

(setq *autolisp-reference-parts* (cons (list (cons "vlr-wblock-reactor" *autolisp-reference-entry*)) *autolisp-reference-parts*))

(setq *autolisp-reference-entry* nil)

(setq *autolisp-reference-value* "GUID-D216131E-A9B6-44AE-8994-E76C7068723C")

(setq *autolisp-reference-entry* (cons (cons 'guid *autolisp-reference-value*) *autolisp-reference-entry*))

(setq *autolisp-reference-value* "https://help.autodesk.com/cloudhelp/2023/ENU/AutoCAD-AutoLISP-Reference/files/GUID-D216131E-A9B6-44AE-8994-E76C7068723C.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following Window reactor events:\n- Window reactor events Event name Description :vlr-docFrameMovedOrResized An MDI child frame window (a document window) has been moved or resized. :vlr-mainFrameMovedOrResized The main AutoCAD window has been moved or resized.\n- callback_function is a symbol representing a function to be called when the event fires. Each callback function accepts two arguments:\n- reactor_object -- The VLR object that called the callback function.\n- list -- A list of extra data elements associated with the particular event. The contents of this list for particular events are shown in the “Window reactor callback data” table.\n- Window reactor callback data Name List length Parameters :vlr-docFrameMovedOrResized :vlr-mainFrameMovedOrResized 2 The first param")

(setq *autolisp-reference-string* (strcat *autolisp-reference-string* "eter is an integer containing the HWND of the window. The second parameter indicates whether the window has been moved or resized. The value is T if the window has been moved, nil if the window has been resized."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-window-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of an event related to moving or sizing an AutoCAD window")

(setq *autolisp-reference-entry* (cons (cons 'summary *autolisp-reference-value*) *autolisp-reference-entry*))

(setq *autolisp-reference-value* "vlr-window-reactor (AutoLISP/ActiveX)")

(setq *autolisp-reference-entry* (cons (cons 'title *autolisp-reference-value*) *autolisp-reference-entry*))

(setq *autolisp-reference-value* "vlr-window-reactor")

(setq *autolisp-reference-entry* (cons (cons 'name *autolisp-reference-value*) *autolisp-reference-entry*))

(setq *autolisp-reference-parts* (cons (list (cons "vlr-window-reactor" *autolisp-reference-entry*)) *autolisp-reference-parts*))

(setq *autolisp-reference-entry* nil)

(setq *autolisp-reference-value* "GUID-E2F57EC0-D78B-438A-A8EC-03F368D8CFD7")

(setq *autolisp-reference-entry* (cons (cons 'guid *autolisp-reference-value*) *autolisp-reference-entry*))

(setq *autolisp-reference-value* "https://help.autodesk.com/cloudhelp/2023/ENU/AutoCAD-AutoLISP-Reference/files/GUID-E2F57EC0-D78B-438A-A8EC-03F368D8CFD7.htm")

(setq *autolisp-reference-entry* (cons (cons 'url *autolisp-reference-value*) *autolisp-reference-entry*))

(setq *autolisp-reference-value* "N/A")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: VLR object\nThe reactor_object argument from the callback_function.")

(setq *autolisp-reference-entry* (cons (cons 'return-values *autolisp-reference-value*) *autolisp-reference-entry*))

(setq *autolisp-reference-value* nil)

(setq *autolisp-reference-string* "Type: List\nA list of pairs of the following form:\n(event-name . callback_function)\n- event-name is one of the following XREF reactor events:\n- XREF reactor events Event name Description :VLR-beginAttach An xref is about to be attached. :VLR-otherAttach An external reference is being added to the drawing database. This event occurs after objects are cloned, but before any translation. This callback function is sent just after beginDeepCloneXlation notification, but occurs only for the xref attach process. :VLR-abortAttach An xref attach operation was terminated before successful completion. :VLR-endAttach An xref attach operation completed successfully. :VLR-redirected An object ID in the xref drawing is being modified to point to the associated object in the drawing being referenced. :VLR-comandeered The object ID of the object is being appended to the symbol table of the drawing bei")

(setq *autolisp-reference-string* (strcat *autolisp-reference-string* "ng xrefed into. :VLR-beginRestore An existing xref is about to be resolved (typically when a drawing with xrefs is loading). :VLR-abortRestore An xref unload or reload was terminated before successful completion. :VLR-endRestore An existing xref has been resolved (typically when a drawing with xrefs has completed loading). :VLR-xrefSubcommandBindItem The BIND subcommand of XREF was invoked, or a preexisting xref is being bound. Note: The BIND subcommand is interactive and triggers multiple events. :VLR-xrefSubcommandAttachItem The ATTACH subcommand of XREF was invoked, or a preexisting xref is being resolved. Note: The ATTACH subcommand is interactive and triggers multiple events. :VLR-xrefSubcommandOverlayItem The OVERLAY subcommand of XREF was invoked, or a preexisting xref is being resolved. Note: The OVERLAY subcommand is interactive and triggers multiple events. :VLR-xrefSubcommandD"))

(setq *autolisp-reference-string* (strcat *autolisp-reference-string* "etachItem The DETACH subcommand of XREF was invoked. Note: The DETACH subcommand is interactive and triggers multiple events. :VLR-xrefSubcommandPathItem The PATH subcommand of XREF was invoked. Note: The PATH subcommand is interactive and triggers multiple events. :VLR-xrefSubcommandReloadItem The RELOAD subcommand of XREF was invoked, or a preexisting xref is being reloaded. Note: The RELOAD subcommand is interactive and triggers multiple events. :VLR-xrefSubcommandUnloadItem The UNLOAD subcommand of XREF was invoked, or a preexisting xref is being unloaded.\n- callback_function is a symbol representing a function to be called when the event fires. Each callback function accepts two arguments:\n- reactor_object -- The VLR object that called the callback function.\n- list -- A list of extra data elements associated with the particular event. The contents of this list for particular even"))

(setq *autolisp-reference-string* (strcat *autolisp-reference-string* "ts are shown in the “XREF reactor callback data” table.\n- XREF reactor callback data Name List length Parameters :VLR-beginAttach 3 First parameter is a VLA-object pointing to the target drawing database. Second parameter is a string containing the file name of the xref being attached. Third parameter is a VLA-object pointing to the drawing database that contains the objects being attached. :VLR-otherAttach 2 First parameter is a VLA-object pointing to the target drawing database. Second parameter is a VLA-object pointing to the drawing database that contains the objects being attached. :VLR-abortAttach 1 A VLA-object pointing to the drawing database that contains the objects being attached. :VLR-endAttach 1 A VLA-object pointing to the target drawing database. :VLR-redirected 2 First parameter is an integer containing the object ID for the redirected symbol table record (STR) in the dr"))

(setq *autolisp-reference-string* (strcat *autolisp-reference-string* "awing being referenced. Second parameter is an integer containing the object ID for the object in the xref drawing. :VLR-comandeered 3 First parameter is a VLA-object pointing to the database receiving the xref. Second parameter is an integer containing the object ID of the object being commandeered. Third parameter is a VLA-object pointing to the drawing database that contains the objects being attached. :VLR-beginRestore 3 First parameter is a VLA-object pointing to the database receiving the xref. Second parameter is a string containing the xref block table record (BTR) name. Third parameter is a VLA-object pointing to the drawing database that contains the objects being attached. :VLR-abortRestore :VLR-endRestore 1 A VLA-object pointing to the target drawing database. :VLR-xrefSubcommandBindItem 2 First parameter is an integer indicating the activity the BIND is carrying out. Possibl"))

(setq *autolisp-reference-string* (strcat *autolisp-reference-string* "e values are 0 -- BIND subcommand invoked. 2 -- xref with the indicated object ID is being bound. 3 -- xref with the indicated object ID was successfully bound. 4 -- BIND subcommand completed. 5 -- BIND operation is about to either terminate or fail to complete on the specified object ID. 6 -- BIND operation has either terminated or failed to complete on the specified object ID. 7 -- Sent for an XDep block bound by XBind. 8 -- Sent for all other symbols: Layers, Linetypes, TextStyles, and DimStyles. Second parameter is an integer containing the object ID of the xref being bound, or 0 if not applicable. :VLR-xrefSubcommandAttachItem 2 First parameter is an integer indicating the activity the ATTACH is carrying out. Possible values are 0 -- BIND subcommand invoked. 2 -- xref with the indicated object ID is being bound. 3 -- xref with the indicated object ID was successfully bound. 4 -- BIN"))

(setq *autolisp-reference-string* (strcat *autolisp-reference-string* "D subcommand completed. 5 -- BIND operation is about to either terminate or fail to complete on the specified object ID. 6 -- BIND operation has either terminated or failed to complete on the specified object ID. Second parameter is a string identifying the file being attached; otherwise nil if not applicable. :VLR-xrefSubcommandOverlayItem 2 First parameter is an integer indicating the activity the OVERLAY is carrying out. Possible values are 0 -- BIND subcommand invoked. 2 -- xref with the indicated object ID is being bound. 3 -- xref with the indicated object ID was successfully bound. 4 -- BIND subcommand completed. 5 -- BIND operation is about to either terminate or fail to complete on the specified object ID. 6 -- BIND operation has either terminated or failed to complete on the specified object ID. Second parameter is a string identifying the file being overlaid; otherwise nil if "))

(setq *autolisp-reference-string* (strcat *autolisp-reference-string* "not applicable. :VLR-xrefSubcommandDetachItem 2 First parameter is an integer indicating the activity the DETACH is carrying out. Possible values are 0 -- BIND subcommand invoked. 2 -- xref with the indicated object ID is being bound. 3 -- xref with the indicated object ID was successfully bound. 4 -- BIND subcommand completed. 5 -- BIND operation is about to either terminate or fail to complete on the specified object ID. 6 -- BIND operation has either terminated or failed to complete on the specified object ID. Second parameter is an integer containing the object ID of the xref being detached, or 0 if not applicable. :VLR-xrefSubcommandPathItem 3 First parameter is an integer indicating the activity the DETACH is carrying out. Possible values are 0 -- BIND subcommand invoked. 2 -- xref with the indicated object ID is being bound. 3 -- xref with the indicated object ID was successfully "))

(setq *autolisp-reference-string* (strcat *autolisp-reference-string* "bound. 4—BIND subcommand completed. 5 -- BIND operation is about to either terminate or fail to complete on the specified object ID. 6 -- BIND operation has either terminated or failed to complete on the specified object ID. Second parameter is an integer containing the object ID of the xref being operated on, or 0 if not applicable. Third parameter is a string identifying the new path name of the xref; otherwise nil if not applicable. :VLR-xrefSubcommandReloadItem 2 First parameter is an integer indicating the activity the RELOAD is carrying out. Possible values are 0 -- BIND subcommand invoked. 2 -- xref with the indicated object ID is being bound. 3 -- xref with the indicated object ID was successfully bound. 4 -- BIND subcommand completed. 5 -- BIND operation is about to either terminate or fail to complete on the specified object ID. 6 -- BIND operation has either terminated or fail"))

(setq *autolisp-reference-string* (strcat *autolisp-reference-string* "ed to complete on the specified object ID. Second parameter is an integer containing the object ID of the xref being reloaded, or 0 if not applicable. :VLR-xrefSubcommandUnloadItem 2 First parameter is an integer indicating the activity the UNLOAD is carrying out. Possible values are 0 -- BIND subcommand invoked. 2 -- xref with the indicated object ID is being bound. 3 -- xref with the indicated object ID was successfully bound. 4 -- BIND subcommand completed. 5 -- BIND operation is about to either terminate or fail to complete on the specified object ID. 6 -- BIND operation has either terminated or failed to complete on the specified object ID. Second parameter is an integer containing the object ID of the xref being unloaded, or 0 if not applicable."))

(setq *autolisp-reference-value* (cons (cons "callbacks" *autolisp-reference-string*) *autolisp-reference-value*))

(setq *autolisp-reference-string* "Type: Integer, Real, String, List, VLA-object, Safearray, Variant, T, or nil\nAny AutoLISP data to be associated with the reactor object; otherwise nil if no data.")

(setq *autolisp-reference-value* (cons (cons "data" *autolisp-reference-string*) *autolisp-reference-value*))

(setq *autolisp-reference-entry* (cons (cons 'arguments *autolisp-reference-value*) *autolisp-reference-entry*))

(setq *autolisp-reference-value* "(vlr-xref-reactor data callbacks)")

(setq *autolisp-reference-entry* (cons (cons 'signature *autolisp-reference-value*) *autolisp-reference-entry*))

(setq *autolisp-reference-value* "Windows only")

(setq *autolisp-reference-entry* (cons (cons 'supported-platforms *autolisp-reference-value*) *autolisp-reference-entry*))

(setq *autolisp-reference-value* '("Reactor Functions Reference (AutoLISP/ActiveX)"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP/ActiveX")

(setq *autolisp-reference-entry* (cons (cons 'source-kind *autolisp-reference-value*) *autolisp-reference-entry*))

(setq *autolisp-reference-value* "Constructs an editor reactor object that notifies of an event related to attaching or modifying XREFs")

(setq *autolisp-reference-entry* (cons (cons 'summary *autolisp-reference-value*) *autolisp-reference-entry*))

(setq *autolisp-reference-value* "vlr-xref-reactor (AutoLISP/ActiveX)")

(setq *autolisp-reference-entry* (cons (cons 'title *autolisp-reference-value*) *autolisp-reference-entry*))

(setq *autolisp-reference-value* "vlr-xref-reactor")

(setq *autolisp-reference-entry* (cons (cons 'name *autolisp-reference-value*) *autolisp-reference-entry*))

(setq *autolisp-reference-parts* (cons (list (cons "vlr-xref-reactor" *autolisp-reference-entry*)) *autolisp-reference-parts*))

(setq *autolisp-reference-entry* nil)

(setq *autolisp-reference-value* "GUID-929FC8B2-1235-4B2A-B330-FF2E219E072C")

(setq *autolisp-reference-entry* (cons (cons 'guid *autolisp-reference-value*) *autolisp-reference-entry*))

(setq *autolisp-reference-value* "https://help.autodesk.com/cloudhelp/2023/ENU/AutoCAD-AutoLISP-Reference/files/GUID-929FC8B2-1235-4B2A-B330-FF2E219E072C.htm")

(setq *autolisp-reference-entry* (cons (cons 'url *autolisp-reference-value*) *autolisp-reference-entry*))

(setq *autolisp-reference-value* "Given a single-viewport configuration with TILEMODE on, the vports function might return the following:\n\n((1 (0.0 0.0) (1.0 1.0)))\n\nGiven four equal-sized viewports located in the four corners of the screen when TILEMODE is on, the vports function might return the following lists:\n\n((5 (0.5 0.0) (1.0 0.5))\n (2 (0.5 0.5) (1.0 1.0))\n (3 (0.0 0.5) (0.5 1.0))\n (4 (0.0 0.0) (0.5 0.5)))\n\nThe current viewport's descriptor is always first in the list. In the previous example, viewport number 5 is the current viewport.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: List\nOne or more viewport descriptor lists consisting of the viewport identification number and the coordinates of the viewport's lower-left and upper-right corners.\nIf the AutoCAD TILEMODE system variable is set to 1 (on), the returned list describes the viewport configuration created with the AutoCAD VPORTS command. The corners of the viewports are expressed in values between 0.0 and 1.0, with (0.0, 0.0) representing the lower-left corner of the display screen's graphics area, and (1.0, 1.0) the upper-right corner. If TILEMODE is 0 (off), the returned list describes the viewport objects created with the AutoCAD MVIEW command. The viewport object corners are expressed in paper space coordinates. Viewport number 1 is always paper space when TILEMODE is off.")

(setq *autolisp-reference-entry* (cons (cons 'return-values *autolisp-reference-value*) *autolisp-reference-entry*))

(setq *autolisp-reference-value* nil)

(setq *autolisp-reference-entry* (cons (cons 'arguments *autolisp-reference-value*) *autolisp-reference-entry*))

(setq *autolisp-reference-value* "(vports)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Display Control"))

(setq *autolisp-reference-entry* (cons (cons 'feature-groups *autolisp-reference-value*) *autolisp-reference-entry*))

(setq *autolisp-reference-value* "V")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns a list of viewport descriptors for the current viewport configuration")

(setq *autolisp-reference-entry* (cons (cons 'summary *autolisp-reference-value*) *autolisp-reference-entry*))

(setq *autolisp-reference-value* "vports (AutoLISP)")

(setq *autolisp-reference-entry* (cons (cons 'title *autolisp-reference-value*) *autolisp-reference-entry*))

(setq *autolisp-reference-value* "vports")

(setq *autolisp-reference-entry* (cons (cons 'name *autolisp-reference-value*) *autolisp-reference-entry*))

(setq *autolisp-reference-parts* (cons (list (cons "vports" *autolisp-reference-entry*)) *autolisp-reference-parts*))

(setq *autolisp-reference-entry* nil)

(setq *autolisp-reference-value* "GUID-EC257AF7-72D4-4B38-99B6-9B09952A53AD")

(setq *autolisp-reference-entry* (cons (cons 'guid *autolisp-reference-value*) *autolisp-reference-entry*))

(setq *autolisp-reference-value* "https://help.autodesk.com/cloudhelp/2023/ENU/AutoCAD-AutoLISP-Reference/files/GUID-EC257AF7-72D4-4B38-99B6-9B09952A53AD.htm")

(setq *autolisp-reference-entry* (cons (cons 'url *autolisp-reference-value*) *autolisp-reference-entry*))

(setq *autolisp-reference-value* "Examples\n\nThe following command tests a string to see if it begins with the character N:\n\n(wcmatch \"Name\" \"N*\")\nT\n\nThe following example performs three comparisons. If any of the three pattern conditions is met, wcmatch returns T. The tests are:\n\nIf any of the three pattern conditions is met, wcmatch returns T:\n\n(wcmatch \"Name\" \"???,~*m*,N*\")\nT\n\nIn this example, the last condition was met, so wcmatch returned T.")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: String or nil\nIf str and pattern match, wcmatch returns T; otherwise, wcmatch returns nil.")

(setq *autolisp-reference-entry* (cons (cons 'return-values *autolisp-reference-value*) *autolisp-reference-entry*))

(setq *autolisp-reference-value* nil)

(setq *autolisp-reference-string* "Type: String\nPattern to match against str. The pattern can contain the wild-card pattern-matching characters shown in the table Wild-card characters. You can use commas in a pattern to enter more than one pattern condition. Only the first 500 characters (approximately) of the str and pattern are compared; anything beyond that is ignored.")

(setq *autolisp-reference-value* (cons (cons "pattern" *autolisp-reference-string*) *autolisp-reference-value*))

(setq *autolisp-reference-string* "Type: String\nA textual value to be compared. The comparison is case-sensitive, so uppercase and lowercase characters must match.")

(setq *autolisp-reference-value* (cons (cons "str" *autolisp-reference-string*) *autolisp-reference-value*))

(setq *autolisp-reference-entry* (cons (cons 'arguments *autolisp-reference-value*) *autolisp-reference-entry*))

(setq *autolisp-reference-value* "(wcmatch str pattern)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("String-Handling"))

(setq *autolisp-reference-entry* (cons (cons 'feature-groups *autolisp-reference-value*) *autolisp-reference-entry*))

(setq *autolisp-reference-value* "W")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Performs a wild-card pattern match on a string")

(setq *autolisp-reference-entry* (cons (cons 'summary *autolisp-reference-value*) *autolisp-reference-entry*))

(setq *autolisp-reference-value* "wcmatch (AutoLISP)")

(setq *autolisp-reference-entry* (cons (cons 'title *autolisp-reference-value*) *autolisp-reference-entry*))

(setq *autolisp-reference-value* "wcmatch")

(setq *autolisp-reference-entry* (cons (cons 'name *autolisp-reference-value*) *autolisp-reference-entry*))

(setq *autolisp-reference-parts* (cons (list (cons "wcmatch" *autolisp-reference-entry*)) *autolisp-reference-parts*))

(setq *autolisp-reference-parts*
  (cons
    '(("while" .
          ((name . "while")
           (title . "while (AutoLISP)")
           (summary . "Evaluates a test expression, and if it is not nil, evaluates other expressions; repeats this process until the test expression evaluates to nil")
           (source-kind . "AutoLISP")
           (alphabetic-group . "W")
           (feature-groups . ("Equality and Conditional"))
           (supported-platforms . "Windows and Mac OS")
           (signature . "(while testexpr [expr ...])")
           (arguments . (("testexpr" . "Type: Integer, Real, String, List, Symbol, File, Ename (entity name), T, or nil\nThe expression containing the test condition.")
                           ("expr" . "Type: Integer, Real, String, List, Symbol, File, Ename (entity name), T, or nil\nOne or more expressions to be evaluated until testexpr is nil.")))
           (return-values . "Type: Integer, Real, String, List, Symbol, File, Ename (entity name), T, or nil\nThe most recent value of the last expr.")
           (release-information . nil)
           (history . nil)
           (examples . "The following code calls user function some-func ten times, with test set to 1 through 10. It then returns 11, which is the value of the last expression evaluated:\n\n(setq test 1)\n(while (<= test 10)\n  (some-func test)\n  (setq test (1+ test))\n)")
           (url . "https://help.autodesk.com/cloudhelp/2023/ENU/AutoCAD-AutoLISP-Reference/files/GUID-E7C900DB-8B66-4109-BEF6-B0A18E8CF6B6.htm")
           (guid . "GUID-E7C900DB-8B66-4109-BEF6-B0A18E8CF6B6"))))
    *autolisp-reference-parts*))

(setq *autolisp-reference-entry* nil)

(setq *autolisp-reference-value* "GUID-83AA4A55-C6A0-447B-A106-717E08D2EAF1")

(setq *autolisp-reference-entry* (cons (cons 'guid *autolisp-reference-value*) *autolisp-reference-entry*))

(setq *autolisp-reference-value* "https://help.autodesk.com/cloudhelp/2023/ENU/AutoCAD-AutoLISP-Reference/files/GUID-83AA4A55-C6A0-447B-A106-717E08D2EAF1.htm")

(setq *autolisp-reference-entry* (cons (cons 'url *autolisp-reference-value*) *autolisp-reference-entry*))

(setq *autolisp-reference-value* "The following command writes the letter C to the command window, and returns the supplied num argument:\n\n(write-char 67)\nC67\n\nAssuming that f is the descriptor for an open file, the following command writes the letter C to that file:\n\n(write-char 67 f)\n67")

(setq *autolisp-reference-entry* (cons (cons 'examples *autolisp-reference-value*) *autolisp-reference-entry*))

(setq *autolisp-reference-value* "AutoCAD 2021\n- num\n- argument previously accepted an ASCII character code in the range of 1-255, but now accepts an integer that represents a Unicode character code in the range of 1-65536.\n- Return value was modified to support Unicode characters and might be different than earlier releases. For example,\n- (write-char 128)\n- previously returned \"€\", but now returns \"\". If you want to return \"€\", your code will need to be updated to\n- (write-char 8364)\n- .\n- (setq fp (open \"E:\\\\test.txt\" \"w\" \"utf8\"))\n- (write-char fp 8364)\n- 8364\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: Integer\nThe num argument.")

(setq *autolisp-reference-entry* (cons (cons 'return-values *autolisp-reference-value*) *autolisp-reference-entry*))

(setq *autolisp-reference-value* nil)

(setq *autolisp-reference-string* "Type: File\nA file descriptor for an open file.")

(setq *autolisp-reference-value* (cons (cons "file-desc" *autolisp-reference-string*) *autolisp-reference-value*))

(setq *autolisp-reference-string* "Type: Integer\nThe integer value in the range of 1-65536 representing the character to be written.")

(setq *autolisp-reference-value* (cons (cons "num" *autolisp-reference-string*) *autolisp-reference-value*))

(setq *autolisp-reference-entry* (cons (cons 'arguments *autolisp-reference-value*) *autolisp-reference-entry*))

(setq *autolisp-reference-value* "(write-char num [file-desc])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "W")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Writes one character to the screen or an open file")

(setq *autolisp-reference-entry* (cons (cons 'summary *autolisp-reference-value*) *autolisp-reference-entry*))

(setq *autolisp-reference-value* "write-char (AutoLISP)")

(setq *autolisp-reference-entry* (cons (cons 'title *autolisp-reference-value*) *autolisp-reference-entry*))

(setq *autolisp-reference-value* "write-char")

(setq *autolisp-reference-entry* (cons (cons 'name *autolisp-reference-value*) *autolisp-reference-entry*))

(setq *autolisp-reference-parts* (cons (list (cons "write-char" *autolisp-reference-entry*)) *autolisp-reference-parts*))

(setq *autolisp-reference-entry* nil)

(setq *autolisp-reference-value* "GUID-CB4F3ABC-F0F6-41DA-A911-75B90D9F974A")

(setq *autolisp-reference-entry* (cons (cons 'guid *autolisp-reference-value*) *autolisp-reference-entry*))

(setq *autolisp-reference-value* "https://help.autodesk.com/cloudhelp/2023/ENU/AutoCAD-AutoLISP-Reference/files/GUID-CB4F3ABC-F0F6-41DA-A911-75B90D9F974A.htm")

(setq *autolisp-reference-entry* (cons (cons 'url *autolisp-reference-value*) *autolisp-reference-entry*))

(setq *autolisp-reference-value* "Windows\n\nOpen a file:\n(setq f (open \"c:\\\\my documents\\\\new.tst\" \"w\"))\n#<file \"c:\\\\my documents\\\\new.tst\">\nUse write-line to write a line to the file:\n(write-line \"To boldly go where nomad has gone before.\" f)\n\"To boldly go where nomad has gone before.\"\nThe line is not physically written until you close the file:\n(close f)\nnil\n\nMac OS\n\nOpen a file:\n(setq f (open \"/my documents/new.tst\" \"w\"))\n#<file \"/my documents/new.tst\">\nUse write-line to write a line to the file:\n(write-line \"To boldly go where nomad has gone before.\" f)\n\"To boldly go where nomad has gone before.\"\nThe line is not physically written until you close the file:\n(close f)\nnil")

(setq *autolisp-reference-entry* (cons (cons 'examples *autolisp-reference-value*) *autolisp-reference-entry*))

(setq *autolisp-reference-value* "AutoCAD 2021\n- str\n- argument previously accepted an ASCII text string or character, but now accepts a Unicode text string or character.\n- Return value was modified to support Unicode characters and might be different than earlier releases.\n- LISPSYS system variable controls which AutoLISP engine is used and the behavior of the function.\n-   - 0 - ASCII character support (legacy behavior)\n-   - 1 or 2 - Unicode character support\n- Note: After the value of the LISPSYS system variable has been changed, AutoCAD must be restarted for the change to take affect.")

(setq *autolisp-reference-entry* (cons (cons 'history *autolisp-reference-value*) *autolisp-reference-entry*))

(setq *autolisp-reference-value* "Releases:\n- AutoCAD R12 and later on Windows\n- AutoCAD 2011 and later on Mac OS")

(setq *autolisp-reference-entry* (cons (cons 'release-information *autolisp-reference-value*) *autolisp-reference-entry*))

(setq *autolisp-reference-value* "Type: String\nThe str, quoted in the normal manner. The quotes are omitted when writing to a file.")

(setq *autolisp-reference-entry* (cons (cons 'return-values *autolisp-reference-value*) *autolisp-reference-entry*))

(setq *autolisp-reference-value* nil)

(setq *autolisp-reference-string* "Type: File\nA file descriptor for an open file.")

(setq *autolisp-reference-value* (cons (cons "file-desc" *autolisp-reference-string*) *autolisp-reference-value*))

(setq *autolisp-reference-string* "Type: String\nA textual value.")

(setq *autolisp-reference-value* (cons (cons "str" *autolisp-reference-string*) *autolisp-reference-value*))

(setq *autolisp-reference-entry* (cons (cons 'arguments *autolisp-reference-value*) *autolisp-reference-entry*))

(setq *autolisp-reference-value* "(write-line str [file-desc])")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("File-Handling"))

(setq *autolisp-reference-entry* (cons (cons 'feature-groups *autolisp-reference-value*) *autolisp-reference-entry*))

(setq *autolisp-reference-value* "W")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Writes a string to the screen or to an open file")

(setq *autolisp-reference-entry* (cons (cons 'summary *autolisp-reference-value*) *autolisp-reference-entry*))

(setq *autolisp-reference-value* "write-line (AutoLISP)")

(setq *autolisp-reference-entry* (cons (cons 'title *autolisp-reference-value*) *autolisp-reference-entry*))

(setq *autolisp-reference-value* "write-line")

(setq *autolisp-reference-entry* (cons (cons 'name *autolisp-reference-value*) *autolisp-reference-entry*))

(setq *autolisp-reference-parts* (cons (list (cons "write-line" *autolisp-reference-entry*)) *autolisp-reference-parts*))

(setq *autolisp-reference-parts*
  (cons
    '(("xdroom" .
          ((name . "xdroom")
           (title . "xdroom (AutoLISP)")
           (summary . "Returns the amount of extended data (xdata) space that is available for an object (entity)")
           (source-kind . "AutoLISP")
           (alphabetic-group . "X")
           (feature-groups . ("Extended Data-Handling"))
           (supported-platforms . "Windows and Mac OS")
           (signature . "(xdroom ename)")
           (arguments . (("ename" . "Type: Ename (entity name)\nAn entity name.")))
           (return-values . "Type: Integer or nil\nAn integer reflecting the number of bytes of available space. If unsuccessful, xdroom returns nil.")
           (release-information . nil)
           (history . nil)
           (examples . "The following example looks up the available space for extended data of a viewport object:\n\n(xdroom vpname)\n16162\n\nIn this example, 16,162 bytes of the original 16,383 bytes of extended data space are available, meaning that 221 bytes are used.")
           (url . "https://help.autodesk.com/cloudhelp/2023/ENU/AutoCAD-AutoLISP-Reference/files/GUID-B7AD1D4B-FAFD-40F2-8A7C-7E35EC23F1FB.htm")
           (guid . "GUID-B7AD1D4B-FAFD-40F2-8A7C-7E35EC23F1FB"))))
    *autolisp-reference-parts*))

(setq *autolisp-reference-entry* nil)

(setq *autolisp-reference-value* "GUID-F183738E-43BC-4820-AC51-5D0C1A3DA38C")

(setq *autolisp-reference-entry* (cons (cons 'guid *autolisp-reference-value*) *autolisp-reference-entry*))

(setq *autolisp-reference-value* "https://help.autodesk.com/cloudhelp/2023/ENU/AutoCAD-AutoLISP-Reference/files/GUID-F183738E-43BC-4820-AC51-5D0C1A3DA38C.htm")

(setq *autolisp-reference-entry* (cons (cons 'url *autolisp-reference-value*) *autolisp-reference-entry*))

(setq *autolisp-reference-value* "The lst can start with a -3 group code (the extended data sentinel), but it is not required. Because extended data can contain information from multiple applications, the list must have a set of enclosing parentheses.\n\n(-3 (\"MYAPP\" (1000 . \"SUITOFARMOR\")\n             (1002 . \"{\")\n             (1040 . 0.0)\n             (1040 . 1.0)\n             (1002 . \"}\")\n   )\n)\n\nHere is the same example without the -3 group code. This list is just the cdr of the first example, but it is important that the enclosing parentheses are included:\n\n( (\"MYAPP\" (1000 . \"SUITOFARMOR\")\n           (1002 . \"{\")\n           (1040 . 0.0)\n           (1040 . 1.0)\n           (1002 . \"}\")\n   )\n)")

(setq *autolisp-reference-entry* (cons (cons 'examples *autolisp-reference-value*) *autolisp-reference-entry*))

(setq *autolisp-reference-value* nil)

(setq *autolisp-reference-entry* (cons (cons 'history *autolisp-reference-value*) *autolisp-reference-entry*))

(setq *autolisp-reference-value* nil)

(setq *autolisp-reference-entry* (cons (cons 'release-information *autolisp-reference-value*) *autolisp-reference-entry*))

(setq *autolisp-reference-value* "Type: Integer\nAn integer reflecting the size, in bytes. If unsuccessful, xdsize returns nil.\nBrace fields (group code 1002) must be balanced. An invalid lst generates an error and places the appropriate error code in the AutoCAD ERRNO system variable. If the extended data contains an unregistered application name, you see this error message (assuming that the AutoCAD CMDECHO system variable is on):\nInvalid application name in 1001 group")

(setq *autolisp-reference-entry* (cons (cons 'return-values *autolisp-reference-value*) *autolisp-reference-entry*))

(setq *autolisp-reference-value* nil)

(setq *autolisp-reference-string* "Type: List\nA valid list of extended data that contains an application name previously registered with the use of the regapp function.")

(setq *autolisp-reference-value* (cons (cons "lst" *autolisp-reference-string*) *autolisp-reference-value*))

(setq *autolisp-reference-entry* (cons (cons 'arguments *autolisp-reference-value*) *autolisp-reference-entry*))

(setq *autolisp-reference-value* "(xdsize lst)")

(setq *autolisp-reference-entry* (cons (cons 'signature *autolisp-reference-value*) *autolisp-reference-entry*))

(setq *autolisp-reference-value* "Windows and Mac OS")

(setq *autolisp-reference-entry* (cons (cons 'supported-platforms *autolisp-reference-value*) *autolisp-reference-entry*))

(setq *autolisp-reference-value* '("Extended Data-Handling"))

(setq *autolisp-reference-entry* (cons (cons 'feature-groups *autolisp-reference-value*) *autolisp-reference-entry*))

(setq *autolisp-reference-value* "X")

(setq *autolisp-reference-entry* (cons (cons 'alphabetic-group *autolisp-reference-value*) *autolisp-reference-entry*))

(setq *autolisp-reference-value* "AutoLISP")

(setq *autolisp-reference-entry* (cons (cons 'source-kind *autolisp-reference-value*) *autolisp-reference-entry*))

(setq *autolisp-reference-value* "Returns the size (in bytes) that a list occupies when it is linked to an object (entity) as extended data")

(setq *autolisp-reference-entry* (cons (cons 'summary *autolisp-reference-value*) *autolisp-reference-entry*))

(setq *autolisp-reference-value* "xdsize (AutoLISP)")

(setq *autolisp-reference-entry* (cons (cons 'title *autolisp-reference-value*) *autolisp-reference-entry*))

(setq *autolisp-reference-value* "xdsize")

(setq *autolisp-reference-entry* (cons (cons 'name *autolisp-reference-value*) *autolisp-reference-entry*))

(setq *autolisp-reference-parts* (cons (list (cons "xdsize" *autolisp-reference-entry*)) *autolisp-reference-parts*))

(setq *autolisp-reference-parts*
  (cons
    '(("zerop" .
          ((name . "zerop")
           (title . "zerop (AutoLISP)")
           (summary . "Verifies that a number evaluates to zero")
           (source-kind . "AutoLISP")
           (alphabetic-group . "Z")
           (feature-groups . ("Arithmetic"))
           (supported-platforms . "Windows and Mac OS")
           (signature . "(zerop number)")
           (arguments . (("number" . "Type: Integer or Real\nA numeric value.")))
           (return-values . "Type: T or nil\nT if number evaluates to zero; otherwise nil.")
           (release-information . nil)
           (history . nil)
           (examples . "(zerop 0)\nT\n\n(zerop 0.0)\nT\n\n(zerop 0.0001)\nnil")
           (url . "https://help.autodesk.com/cloudhelp/2023/ENU/AutoCAD-AutoLISP-Reference/files/GUID-3D509EE1-A809-4B78-915C-28ECF483BB72.htm")
           (guid . "GUID-3D509EE1-A809-4B78-915C-28ECF483BB72"))))
    *autolisp-reference-parts*))

(setq *autolisp-reference-parts*
  (cons
    '(("~" .
          ((name . "~")
           (title . "~ (bitwise NOT) (AutoLISP)")
           (summary . "Returns the bitwise NOT (1's complement) of the argument")
           (source-kind . "AutoLISP")
           (alphabetic-group . "Non-alphabetic")
           (feature-groups . ("Arithmetic"))
           (supported-platforms . "Windows and Mac OS")
           (signature . "(~ int)")
           (arguments . (("int" . "Type: Integer\nA positive or negative integer value.")))
           (return-values . "Type: Integer\nThe bitwise NOT (1's complement) of the argument.")
           (release-information . nil)
           (history . nil)
           (examples . "(~ 3)\n-4\n\n(~ 100)\n-101\n\n(~ -4)\n3")
           (url . "https://help.autodesk.com/cloudhelp/2023/ENU/AutoCAD-AutoLISP-Reference/files/GUID-98811E38-FCA8-4ADB-858C-60C3828D7DB4.htm")
           (guid . "GUID-98811E38-FCA8-4ADB-858C-60C3828D7DB4"))))
    *autolisp-reference-parts*))

(defun autolisp-build-reference ( / entry part parts result)
  (setq parts (reverse *autolisp-reference-parts*))
  (setq *autolisp-reference-parts* nil)
  (setq *autolisp-reference-entry* nil)
  (setq *autolisp-reference-value* nil)
  (setq *autolisp-reference-string* nil)
  (setq result nil)
  (foreach part parts
    (foreach entry part
      (setq result (cons entry result))))
  (reverse result))

(setq *autolisp-reference* (autolisp-build-reference))

(princ)

;;; autolisp-ref.lsp ends here
